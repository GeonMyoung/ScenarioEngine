Dz1Asn1Test DEFINITIONS AUTOMATIC TAGS ::= BEGIN

--*********************************************************************
-- BOOLEAN(1)
--*********************************************************************
MyBool ::= BOOLEAN

--*********************************************************************
-- INTEGER(2)
--*********************************************************************
MyInt0 ::= INTEGER {
	spec-RevocableLane			(0),
	spec-commuterRailRoadTrack	(1), 
	spec-lightRailRoadTrack		(2),
	spec-heavyRailRoadTrack		(3),
	spec-otherRailType			(4)
} (0..10|100..1000|10000..20000)

MyInt1 ::= [ APPLICATION 21 ] INTEGER(301..10000)
MyInt2 ::= [ APPLICATION 22 ] EXPLICIT INTEGER(101..200)
MyInt3 ::= [ APPLICATION 23 ] IMPLICIT INTEGER(201..300)
MyInt4 ::= [ APPLICATION 24 ] MyInt0
MyInt5 ::= [ APPLICATION 25 ] EXPLICIT MyInt0
MyInt6 ::= [ APPLICATION 26 ] IMPLICIT MyInt0

--*********************************************************************
-- BIT STRING(3)
--*********************************************************************
MyBitStr0 ::= BIT STRING
MyBitStr1 ::= BIT STRING(SIZE(1..4))
MyBitStr2 ::= BIT STRING { 
	spec-RevocableLane			(0),
	spec-commuterRailRoadTrack	(1), 
	spec-lightRailRoadTrack		(2),
	spec-heavyRailRoadTrack		(3),
	spec-otherRailType			(4)
} (SIZE (1..16))
MyBitStr3 ::= MyBitStr2
MyBitStr4 ::= MyBitStr3
MyBitStr5 ::= MyBitStr4

--*********************************************************************
-- OCTET STRING(4)
--*********************************************************************
MyOctet0 ::= OCTET STRING
MyOctet1 ::= OCTET STRING(SIZE(1..1024))

--*********************************************************************
-- NULL(5)
--*********************************************************************
MyNull ::= NULL

--*********************************************************************
-- OBJECT IDENTIFIER(6)
--*********************************************************************
MyOID ::= OBJECT IDENTIFIER

--*********************************************************************
-- ObjectDescriptor(7)
--*********************************************************************
MyObjDescr ::= ObjectDescriptor

--*********************************************************************
-- EXTERNAL(8)
--*********************************************************************
MyExternal ::= EXTERNAL

--*********************************************************************
-- INSTANCE OF(8)
--*********************************************************************
MyInstance ::= INSTANCE OF MY-OBJECT-CLASS

--*********************************************************************
-- REAL(9)
--*********************************************************************
MyReal ::= REAL

--*********************************************************************
-- ENUMERATED(10)
--*********************************************************************
MyEnum0 ::= ENUMERATED
{
	first,
	second,
	third,
	fourth
}
MyEnum1 ::= [APPLICATION 100] EXPLICIT MyEnum0
MyEnum2 ::= [APPLICATION 101] IMPLICIT MyEnum0

--*********************************************************************
-- EMBEDDED PDV(11)
--*********************************************************************
MyEmbodded ::= EMBEDDED PDV

--*********************************************************************
-- UTF8String(12)
--*********************************************************************
MyUtf0 ::= UTF8String
MyUtf1 ::= UTF8String(SIZE(0..1024))

--*********************************************************************
-- RELATIVE-OID(13)
--*********************************************************************
MyROid ::= RELATIVE-OID

--*********************************************************************
-- TIME(14)
--*********************************************************************
MyTime ::= TIME

--*********************************************************************
-- NumericString(18)								  : Known-Multifier
--*********************************************************************
MyDigitStr0 ::= NumericString
MyDigitStr1 ::= NumericString(SIZE(0..100))

--*********************************************************************
-- PrintableString(19)								  : Known-Multifier
--*********************************************************************
MyPrintStr0 ::= PrintableString
MyPrintStr1 ::= PrintableString(SIZE(0..100))

--*********************************************************************
-- TeletexString(20)
--*********************************************************************
MyTeletexStr ::= TeletexString

--*********************************************************************
-- T61String(20)
--*********************************************************************
MyT61Str ::= T61String

--*********************************************************************
-- VideotexString(21)
--*********************************************************************
MyVideotexStr ::= VideotexString

--*********************************************************************
-- IA5String(22)									  : Known-Multifier
--*********************************************************************
MyIA5Str0 ::= IA5String
MyIA5Str1 ::= IA5String(SIZE(0..100))

--*********************************************************************
-- ISO646String(22)									  : Known-Multifier
--*********************************************************************
MyISO646Str0 ::= ISO646String
MyISO646Str1 ::= ISO646String(SIZE(0..100))

--*********************************************************************
-- UTCTime(23)
--*********************************************************************
MyUTCTime ::= UTCTime

--*********************************************************************
-- GeneralizedTime(24)
--*********************************************************************
MyGeneralTime ::= GeneralizedTime

--*********************************************************************
-- GraphicString(25)
--*********************************************************************
MyGraphicStr ::= GraphicString

--*********************************************************************
-- VisibleString(26)								  : Known-Multifier
--*********************************************************************
MyVisibleStr0 ::= VisibleString
MyVisibleStr1 ::= VisibleString(SIZE(0..100))

--*********************************************************************
-- GeneralString(27)
--*********************************************************************
MyGeneralStr ::= GeneralString

--*********************************************************************
-- UniversalString(28)								  : Known-Multifier
--*********************************************************************
MyUniStr0 ::= UniversalString
MyUniStr1 ::= UniversalString(SIZE(0..100))

--*********************************************************************
-- CHARACTER STRING(29)
--*********************************************************************
MyCharStr ::= CHARACTER STRING

--*********************************************************************
-- BMPString(30)									  : Known-Multifier
--*********************************************************************
MyBmpStr0 ::= BMPString
MyBmpStr1 ::= BMPString(SIZE(0..100))

--*********************************************************************
-- DATE(31)
--*********************************************************************
MyDate ::= DATE

--*********************************************************************
-- TIME-OF-DAY(32)
--*********************************************************************
MyTimeOfDay ::= TIME-OF-DAY

--*********************************************************************
-- DATE-TIME(33)
--*********************************************************************
MyDateTime ::= DATE-TIME

--*********************************************************************
-- DURATION(34)
--*********************************************************************
MyDuration ::= DURATION

END
