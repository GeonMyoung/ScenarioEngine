GitsnAsn1 DEFINITIONS AUTOMATIC TAGS ::= BEGIN
PartII-Id ::= INTEGER (0..63)
   vehicleSafetyExt       PartII-Id::= 0  
   specialVehicleExt      PartII-Id::= 1  
   supplementalVehicleExt PartII-Id::= 2  
   



Acceleration ::= INTEGER (-2000..2001) 

AccelerationConfidence ::= ENUMERATED {
  unavailable  (0), 
  accl-100-00  (1), 
  accl-010-00  (2), 
  accl-005-00  (3), 
  accl-001-00  (4), 
  accl-000-10  (5), 
  accl-000-05  (6), 
  accl-000-01  (7)  
} 
  
AdvisorySpeedType ::= ENUMERATED {
  none       (0),
  greenwave  (1),
  ecoDrive   (2),
  transit    (3),
  ...
  }

AllowedManeuvers ::= BIT STRING {
  maneuverStraightAllowed       (0),
  maneuverLeftAllowed           (1),
  maneuverRightAllowed          (2),
  maneuverUTurnAllowed          (3),
  maneuverLeftTurnOnRedAllowed  (4),
  maneuverRightTurnOnRedAllowed (5),
  maneuverLaneChangeAllowed     (6),
  maneuverNoStoppingAllowed     (7),
  yieldAllwaysRequired          (8),
  goWithHalt                    (9),
  caution                       (10),
  reserved1                     (11)
} (SIZE(12))
                                      
AmbientAirPressure ::= INTEGER (0..255) 


AmbientAirTemperature ::= INTEGER (0..191) 

Angle ::= INTEGER (0..28800) 

AnimalPropelledType ::= ENUMERATED {
  unavailable         (0),
  otherTypes          (1), 
  animalMounted       (2), 
  animalDrawnCarriage (3),
  ...
}

AnimalType ::= ENUMERATED {
  unavailable (0),
  serviceUse  (1), 
  pet         (2),
  farm        (3),
  ...
}

AntiLockBrakeStatus ::= ENUMERATED {
  unavailable (0), 
                   
  off         (1), 
  on          (2), 
  engaged     (3)  
}

ApproachID ::= INTEGER (0..15)

Attachment ::= ENUMERATED {
  unavailable                 (0),
  stroller                    (1),
  bicycleTrailer              (2),
  cart                        (3),
  wheelchair                  (4),
  otherWalkAssistAttachments  (5),
  pet                         (6),
  ...
}

AttachmentRadius ::= INTEGER (0..200)

AuxiliaryBrakeStatus ::= ENUMERATED {
  unavailable (0), 
                   
  off         (1), 
  on          (2), 
  reserved    (3)  
}

BasicVehicleClass ::= INTEGER (0..255)
  unknownVehicleClass             BasicVehicleClass ::=  0  
  specialVehicleClass             BasicVehicleClass ::=  1  
  
  
  passenger-Vehicle-TypeUnknown   BasicVehicleClass ::=  10 
  passenger-Vehicle-TypeOther     BasicVehicleClass ::=  11 
  
  
  lightTruck-Vehicle-TypeUnknown  BasicVehicleClass ::=  20 
  lightTruck-Vehicle-TypeOther    BasicVehicleClass ::=  21 
  
  
  truck-Vehicle-TypeUnknown 			BasicVehicleClass ::=  25 
  truck-Vehicle-TypeOther 				BasicVehicleClass ::=  26 
  truck-axleCnt2  								BasicVehicleClass ::=  27 
  truck-axleCnt3  								BasicVehicleClass ::=  28 
  truck-axleCnt4  								BasicVehicleClass ::=  29 
  truck-axleCnt4Trailer 					BasicVehicleClass ::=  30 
  truck-axleCnt5Trailer 					BasicVehicleClass ::=  31 
  truck-axleCnt6Trailer 					BasicVehicleClass ::=  32 
  truck-axleCnt5MultiTrailer 			BasicVehicleClass ::=  33 
  truck-axleCnt6MultiTrailer 			BasicVehicleClass ::=  34 
  truck-axleCnt7MultiTrailer 			BasicVehicleClass ::=  35 
  
  
  motorcycle-TypeUnknown          BasicVehicleClass ::=  40 
  motorcycle-TypeOther            BasicVehicleClass ::=  41
  motorcycle-Cruiser-Standard     BasicVehicleClass ::=  42
  motorcycle-SportUnclad          BasicVehicleClass ::=  43
  motorcycle-SportTouring         BasicVehicleClass ::=  44
  motorcycle-SuperSport           BasicVehicleClass ::=  45
  motorcycle-Touring              BasicVehicleClass ::=  46
  motorcycle-Trike                BasicVehicleClass ::=  47 
  motorcycle-wPassengers          BasicVehicleClass ::=  48 
  
  
  transit-TypeUnknown             BasicVehicleClass ::=  50 
  transit-TypeOther               BasicVehicleClass ::=  51
  transit-BRT                     BasicVehicleClass ::=  52
  transit-ExpressBus              BasicVehicleClass ::=  53
  transit-LocalBus                BasicVehicleClass ::=  54
  transit-SchoolBus               BasicVehicleClass ::=  55
  transit-FixedGuideway           BasicVehicleClass ::=  56
  transit-Paratransit             BasicVehicleClass ::=  57
  transit-Paratransit-Ambulance   BasicVehicleClass ::=  58
  
  
  emergency-TypeUnknown            BasicVehicleClass ::=  60 
  emergency-TypeOther              BasicVehicleClass ::=  61 
  emergency-Fire-Light-Vehicle     BasicVehicleClass ::=  62
  emergency-Fire-Heavy-Vehicle     BasicVehicleClass ::=  63
  emergency-Fire-Paramedic-Vehicle BasicVehicleClass ::=  64
  emergency-Fire-Ambulance-Vehicle BasicVehicleClass ::=  65
  emergency-Police-Light-Vehicle   BasicVehicleClass ::=  66
  emergency-Police-Heavy-Vehicle   BasicVehicleClass ::=  67
  emergency-Other-Responder        BasicVehicleClass ::=  68
	emergency-Other-Ambulance        BasicVehicleClass ::=  69
	
	
	otherTraveler-TypeUnknown          BasicVehicleClass ::=  80 
	otherTraveler-TypeOther            BasicVehicleClass ::=  81
	otherTraveler-Pedestrian           BasicVehicleClass ::=  82
	otherTraveler-Visually-Disabled    BasicVehicleClass ::=  83
	otherTraveler-Physically-Disabled  BasicVehicleClass ::=  84
	otherTraveler-Bicycle              BasicVehicleClass ::=  85
	otherTraveler-Vulnerable-Roadworker BasicVehicleClass ::=  86
	
	
	infrastructure-TypeUnknown      BasicVehicleClass ::=  90 
	infrastructure-Fixed            BasicVehicleClass ::=  91
	infrastructure-Movable          BasicVehicleClass ::=  92
	equipped-CargoTrailer           BasicVehicleClass ::=  93


BasicVehicleRole ::= ENUMERATED {
  basicVehicle     (0), 
  publicTransport  (1), 
  specialTransport (2), 
  dangerousGoods   (3), 
  roadWork         (4), 
  roadRescue       (5), 
  emergency        (6), 
  safetyCar        (7), 
  none-unknown     (8), 
  truck            (9), 
  motorcycle      (10), 
  roadSideSource  (11), 
  police          (12), 
  fire            (13), 
  ambulance       (14), 
  dot             (15), 
  transit         (16), 
  slowMoving      (17), 
  stopNgo         (18), 
  cyclist         (19), 
  pedestrian      (20), 
  nonMotorized    (21), 
  military        (22), 
  ...   
}

BrakeAppliedPressure ::= ENUMERATED {
  unavailable  (0),  
  minPressure  (1),  
  bkLvl-2      (2),  
  bkLvl-3      (3),  
  bkLvl-4      (4),  
  bkLvl-5      (5),  
  bkLvl-6      (6),  
  bkLvl-7      (7),  
  bkLvl-8      (8),  
  bkLvl-9      (9),  
  bkLvl-10     (10), 
  bkLvl-11     (11), 
  bkLvl-12     (12), 
  bkLvl-13     (13), 
  bkLvl-14     (14), 
  maxPressure  (15)  
} 
  
BrakeAppliedStatus ::= BIT STRING {
  unavailable (0),  
  leftFront   (1),  
  leftRear    (2),  
  rightFront  (3),  
  rightRear   (4)   
} (SIZE (5))

BrakeBoostApplied ::= ENUMERATED {
  unavailable   (0), 
  off           (1), 
  on            (2)  
}

BumperHeight ::= INTEGER (0..127) 

CoarseHeading ::= INTEGER (0..240)

CoefficientOfFriction ::= INTEGER (0..50) 

Confidence ::= INTEGER (0..200)

 
DDay ::= INTEGER (0..31)  

DeltaAngle ::= INTEGER (-150..150)

DeltaTime ::= INTEGER (-122 .. 121)

DescriptiveName ::= IA5String (SIZE(1..63))

DHour ::= INTEGER (0..31) 

DirectionOfUse ::= ENUMERATED {
  unavailable  (0),
  forward	   (1),
  reverse	   (2),
  both 		   (3)
}

DistanceUnits ::= ENUMERATED { 
  centimeter(0), 
  cm2-5	 	(1), 
  decimeter	(2), 
  meter		(3), 
  kilometer	(4), 
  foot 	 	(5), 
  yard 		(6), 
  mile 		(7) 
}

DMinute ::= INTEGER (0..60) 

DMonth ::= INTEGER (0..12) 

DOffset ::= INTEGER (-840..840) 

DrivenLineOffsetLg ::= INTEGER (-32767..32767)

DrivenLineOffsetSm ::= INTEGER (-2047..2047)

DrivingWheelAngle ::= INTEGER (-128..127)

DSecond ::= INTEGER (0..65535) 

DSRCmsgID ::= INTEGER (0..32767)

  
  mapData                           DSRCmsgID ::=   18 
  signalPhaseAndTimingMessage       DSRCmsgID ::=   19 
  basicSafetyMessage                DSRCmsgID ::=   20 
  commonSafetyRequest               DSRCmsgID ::=   21 
  emergencyVehicleAlert             DSRCmsgID ::=   22 
  intersectionCollision             DSRCmsgID ::=   23 
  nmeaCorrections                   DSRCmsgID ::=   24 
  probeDataManagement               DSRCmsgID ::=   25 
  probeVehicleData                  DSRCmsgID ::=   26 
  roadSideAlert                     DSRCmsgID ::=   27 
  rtcmCorrections                   DSRCmsgID ::=   28 
  travelerInformation               DSRCmsgID ::=   31 
  personalSafetyMessage             DSRCmsgID ::=   32 
  trafficLightStatusMessage         DSRCmsgID ::=   50 


DYear ::= INTEGER (0..4095) 

ElevationConfidence ::= ENUMERATED {
  unavailable (0),  
  elev-500-00 (1),  
  elev-200-00 (2),  
  elev-100-00 (3),  
  elev-050-00 (4),  
  elev-020-00 (5),  
  elev-010-00 (6),  
  elev-005-00 (7),  
  elev-002-00 (8),  
  elev-001-00 (9),  
  elev-000-50 (10), 
  elev-000-20 (11), 
  elev-000-10 (12), 
  elev-000-05 (13), 
  elev-000-02 (14), 
  elev-000-01 (15)  
} 

Elevation ::= INTEGER (-4096..61439) 

Extent ::= ENUMERATED {
  useInstantlyOnly     (0),
  useFor3meters        (1),
  useFor10meters       (2),
  useFor50meters       (3),
  useFor100meters      (4),
  useFor500meters      (5),
  useFor1000meters     (6),
  useFor5000meters     (7),
  useFor10000meters    (8),
  useFor50000meters    (9),
  useFor100000meters   (10),
  useFor500000meters   (11),
  useFor1000000meters  (12),
  useFor5000000meters  (13),
  useFor10000000meters (14),
  forever              (15)  
}  

ExteriorLights ::= BIT STRING { 
  lowBeamHeadlightsOn       (0), 
  highBeamHeadlightsOn      (1), 
  leftTurnSignalOn          (2), 
  rightTurnSignalOn         (3), 
  hazardSignalOn            (4), 
  automaticLightControlOn   (5),
  daytimeRunningLightsOn    (6), 
  fogLightOn                (7), 
  parkingLightsOn           (8) 
} (SIZE (9, ...))


FuelType ::= INTEGER (0..15)
  unknownFuel   FuelType::=  0 
  gasoline      FuelType::=  1 
  ethanol       FuelType::=  2 
  diesel        FuelType::=  3 
  electric      FuelType::=  4  
  hybrid        FuelType::=  5 
  hydrogen      FuelType::=  6  
  natGasLiquid  FuelType::=  7 
  natGasComp    FuelType::=  8 
  propane       FuelType::=  9  


FurtherInfoID ::= OCTET STRING (SIZE(2))

GNSSstatus ::= BIT STRING {
  unavailable               (0), 
  isHealthy                 (1),
  isMonitored               (2),
  baseStationType           (3), 
  aPDOPofUnder5             (4), 
  inViewOfUnder5            (5), 
  localCorrectionsPresent   (6), 
  networkCorrectionsPresent (7)  
} (SIZE(8))

GrossDistance ::= INTEGER (0..1023)

GrossSpeed ::= INTEGER (0..31) 

HeadingConfidence ::= ENUMERATED {
  unavailable   (0), 
  prec10deg     (1), 
  prec05deg     (2), 
  prec01deg     (3), 
  prec0-1deg    (4), 
  prec0-05deg   (5), 
  prec0-01deg   (6), 
  prec0-0125deg (7)  
}  

Heading ::= INTEGER (0..28800) 

HeadingSlice ::= BIT STRING {
  from000-0to022-5degrees  (0),   
  from022-5to045-0degrees  (1),   
  from045-0to067-5degrees  (2),   
  from067-5to090-0degrees  (3),   
  
  from090-0to112-5degrees  (4),   
  from112-5to135-0degrees  (5),   
  from135-0to157-5degrees  (6),   
  from157-5to180-0degrees  (7),   
  
  from180-0to202-5degrees  (8),   
  from202-5to225-0degrees  (9),   
  from225-0to247-5degrees  (10),  
  from247-5to270-0degrees  (11),  
  
  from270-0to292-5degrees  (12),  
  from292-5to315-0degrees  (13),  
  from315-0to337-5degrees  (14),  
  from337-5to360-0degrees  (15)  
}  (SIZE (16))

IntersectionID ::= INTEGER (0..65535)

IntersectionStatusObject ::= BIT STRING {
  manualControlIsEnabled                (0),
  stopTimeIsActivated                   (1),
  failureFlash                          (2),
  preemptIsActive                       (3),
  signalPriorityIsActive                (4),
  fixedTimeOperation                    (5),
  trafficDependentOperation             (6),
  standbyOperation                      (7),
  failureMode                           (8),
  off                                   (9),
  recentMAPmessageUpdate                (10),
  recentChangeInMAPassignedLanesIDsUsed (11),
  noValidMAPisAvailableAtThisTime       (12),
  noValidSPATisAvailableAtThisTime      (13)
} (SIZE(16))

IsDolly ::= BOOLEAN 

Iso3833VehicleType ::= INTEGER (0..100) 

ITIStextPhrase ::= IA5String (SIZE(1..16))

AxleLocation ::= INTEGER (0..255)

AxleWeight ::= INTEGER (0..64255)

CargoWeight ::= INTEGER (0..64255)

DriveAxleLiftAirPressure ::= INTEGER (0..1000)

DriveAxleLocation ::= INTEGER (0..255)

DriveAxleLubePressure ::= INTEGER (0..250)

DriveAxleTemperature ::= INTEGER (-40..210)

SteeringAxleLubePressure ::= INTEGER (0..250)

SteeringAxleTemperature ::= INTEGER (-40..210)

TireLeakageRate ::= INTEGER (0..64255)

TireLocation ::= INTEGER (0..255)

TirePressureThresholdDetection ::= ENUMERATED {
  noData                (0),  
  overPressure          (1),  
  noWarningPressure     (2),  
  underPressure         (3),  
  extremeUnderPressure  (4),  
  undefined             (5),  
  errorIndicator        (6),  
  notAvailable          (7)   
}

TirePressure ::= INTEGER (0..250)

TireTemp ::= INTEGER (-8736..55519)

TrailerWeight ::= INTEGER (0..64255)

WheelEndElectFault ::= ENUMERATED {
  isOk            (0), 
  isNotDefined    (1),
  isError         (2),
  isNotSupported  (3)
} 

WheelSensorStatus ::= ENUMERATED {
  off           (0), 
  on            (1),
  notDefined    (2), 
  notSupported  (3)
}

LaneAttributes-Barrier ::= BIT STRING {
  median-RevocableLane	(0),
  median                (1),
  whiteLineHashing    (2),
  stripedLines        (3),
  doubleStripedLines	(4),
  trafficCones				(5),
  constructionBarrier	(6),
  trafficChannels			(7),
  lowCurbs						(8),
  highCurbs						(9) 
} (SIZE (16))

LaneAttributes-Bike ::= BIT STRING {
  bikeRevocableLane					(0),
  pedestrianUseAllowed 			(1),
  isBikeFlyOverLane					(2),
  fixedCycleTime 		 	 			(3),
  biDirectionalCycleTimes		(4),
  isolatedByBarrier					(5),  
  unsignalizedSegmentsPresent	(6) 
  } (SIZE (16))

LaneAttributes-Crosswalk ::= BIT STRING { 
  crosswalkRevocableLane		(0),
  bicyleUseAllowed 			    (1),
  isXwalkFlyOverLane				(2),
  fixedCycleTime						(3),
  biDirectionalCycleTimes		(4),
  hasPushToWalkButton				(5),
  audioSupport 							(6),
  rfSignalRequestPresent 		(7),
  unsignalizedSegmentsPresent   (8) 
} (SIZE (16))

LaneAttributes-Parking ::= BIT STRING { 
  parkingRevocableLane	(0),
  parallelParkingInUse	(1),  
  headInParkingInUse   	(2),
  doNotParkZone        	(3),
  parkingForBusUse 		  (4),
  parkingForTaxiUse 	  (5),
  noPublicParkingUse 	  (6) 
} (SIZE (16))

LaneAttributes-Sidewalk ::= BIT STRING {
  sidewalk-RevocableLane	(0),
  bicyleUseAllowed       	(1),
  isSidewalkFlyOverLane  	(2),
  walkBikes               (3)
} (SIZE (16))

LaneAttributes-Striping ::= BIT STRING {
  stripeToConnectingLanesRevocableLane      (0),
  stripeDrawOnLeft                          (1),
  stripeDrawOnRight                         (2),
  stripeToConnectingLanesLeft               (3),
  stripeToConnectingLanesRight              (4),
  stripeToConnectingLanesAhead              (5)
} (SIZE (16))


LaneAttributes-TrackedVehicle ::= BIT STRING { 
  spec-RevocableLane					(0),
  spec-commuterRailRoadTrack	(1), 
  spec-lightRailRoadTrack 	  (2),
  spec-heavyRailRoadTrack 	  (3),
  spec-otherRailType 					(4)
} (SIZE (16))


LaneAttributes-Vehicle ::= BIT STRING { 
  isVehicleRevocableLane	    (0),
  isVehicleFlyOverLane	      (1),
  hovLaneUseOnly 			    		(2),
  restrictedToBusUse 		    	(3),
  restrictedToTaxiUse 		    (4),
  restrictedFromPublicUse	    (5),
  hasIRbeaconCoverage 		    (6), 
  permissionOnRequest 		    (7)  
} (SIZE (8,...))


LaneConnectionID ::= INTEGER (0..255)

LaneDirection ::= BIT STRING {
  ingressPath     (0),
  egressPath      (1)
} (SIZE (2))
  

LaneID ::= INTEGER (0..255)

LaneSharing ::= BIT STRING {
  overlappingLaneDescriptionProvided   (0),
  multipleLanesTreatedAsOneLane        (1),
  otherNonMotorizedTrafficTypes        (2), 
  individualMotorizedVehicleTraffic    (3),
  busVehicleTraffic                    (4),
  taxiVehicleTraffic                   (5),
  pedestriansTraffic                   (6),
  cyclistVehicleTraffic                (7),
  trackedVehicleTraffic                (8),
  reserved                             (9)
} (SIZE (10))

LaneWidth ::= INTEGER (0..32767) 

Latitude ::= INTEGER (-900000000..900000001)  

LayerID ::= INTEGER (0..100)

LayerType ::= ENUMERATED {
  none,
  mixedContent, 
  generalMapData,
  intersectionData,
  curveData,
  roadwaySectionData,
  parkingAreaData,
  sharedLaneData,
  ...
}
    
LightbarInUse ::= ENUMERATED {
  unavailable         (0),  
  notInUse            (1),  
  inUse               (2),  
  yellowCautionLights (3),  
  schooldBusLights    (4),  
  arrowSignsActive    (5),  
  slowMovingVehicle   (6),   
  freqStops           (7)   
}

Longitude ::= INTEGER (-1799999999..1800000001)  


MergeDivergeNodeAngle ::= INTEGER (-180..180)


MinuteOfTheYear ::= INTEGER (0..527040)

MinutesDuration ::= INTEGER (0..32000)

MotorizedPropelledType ::= ENUMERATED {
  unavailable          (0),
  otherTypes           (1), 
  wheelChair           (2),
  bicycle              (3),
  scooter              (4),
  selfBalancingDevice  (5), 
  ...
}


MovementPhaseState ::= ENUMERATED {
  unavailable (0),
  dark (1),
  stop-Then-Proceed (2),
  stop-And-Remain (3),
  pre-Movement (4),
  permissive-Movement-Allowed (5),
  protected-Movement-Allowed (6),
  permissive-clearance (7),
  protected-clearance (8),
  caution-Conflicting-Traffic (9)
}
      

MsgCount ::= INTEGER (0..127)

MsgCRC ::= OCTET STRING (SIZE(2))

MultiVehicleResponse ::= ENUMERATED {
  unavailable 	(0), 
  singleVehicle (1),
  multiVehicle 	(2),
  reserved 			(3) 
}

MUTCDCode ::= ENUMERATED {
  none					(0),
  regulatory		(1), 
  warning 			(2), 
  maintenance 	(3),
  motoristService 	(4), 
  guide 				(5), 
  rec 					(6), 
  ...
}

NMEA-MsgType ::= INTEGER (0..32767)

NMEA-Payload ::= OCTET STRING (SIZE(1..1023))

NMEA-Revision ::= ENUMERATED {
  unknown       (0), 
  reserved      (1),
  rev1          (2),
  rev2          (3), 
  rev3          (4), 
  rev4          (5), 
  rev5          (6),
  ...
}

NodeAttributeLL ::= ENUMERATED {
  reserved, 
  stopLine, 
  roundedCapStyleA,
  roundedCapStyleB, 
  mergePoint,
  divergePoint, 
  downstreamStopLine, 
  downstreamStartNode, 
  closedToTraffic,
  safeIsland, 
  curbPresentAtStepOff, 
  hydrantPresent, 
  ...
}

NodeAttributeXY ::= ENUMERATED {
  reserved,
  stopLine, 
  roundedCapStyleA,
  roundedCapStyleB,
  mergePoint,      
  divergePoint,    
  downstreamStopLine,
  downstreamStartNode,
  closedToTraffic,  
  safeIsland,  
  curbPresentAtStepOff,
  hydrantPresent, 
  ...
}

NumberOfParticipantsInCluster ::= ENUMERATED {
  unavailable (0),
  small       (1), 
  medium      (2), 
  large       (3), 
  ...
}
  
ObjectCount ::= INTEGER (0..1023) 

ObstacleDirection ::= Angle

ObstacleDistance ::= INTEGER (0..32767)

Offset-B09 ::= INTEGER (-256..255)

Offset-B10 ::= INTEGER (-512..511)

Offset-B11 ::= INTEGER (-1024..1023)

Offset-B12 ::= INTEGER (-2048..2047)

Offset-B13 ::= INTEGER (-4096..4095)

Offset-B14 ::= INTEGER (-8192..8191)

Offset-B16 ::= INTEGER (-32768..32767)

OffsetLL-B12 ::= INTEGER (-2048..2047)     

OffsetLL-B14 ::= INTEGER (-8192..8191)     

OffsetLL-B16 ::= INTEGER (-32768..32767)     

OffsetLL-B18 ::= INTEGER (-131072..131071)     

OffsetLL-B22 ::= INTEGER (-2097152..2097151)     

OffsetLL-B24 ::= INTEGER (-8388608..8388607)     

PedestrianBicycleDetect ::= BOOLEAN

HumanPropelledType ::= ENUMERATED {
  unavailable        (0),
  otherTypes         (1),
  onFoot             (2),
  skateboard         (3),
  pushOrKickScooter  (4),
  wheelchair         (5),
  ...
}

PersonalAssistive ::= BIT STRING {
  unavailable  (0),
  otherType    (1),
  vision       (2),
  hearing      (3),
  movement     (4),
  cognition    (5)
} (SIZE (6, ...))

PersonalClusterRadius ::= INTEGER (0..100) 

PersonalCrossingInProgress ::= BOOLEAN 

PersonalCrossingRequest ::= BOOLEAN

PersonalDeviceUsageState ::= BIT STRING {
  unavailable       (0), 
  other             (1), 
  idle              (2), 
  listeningToAudio  (3), 
  typing            (4), 
  calling           (5),
  playingGames      (6),
  reading           (7),
  viewing           (8) 
} (SIZE (9, ...))

PersonalDeviceUserType ::= ENUMERATED {
  unavailable          (0),
  aPEDESTRIAN          (1), 
  aPEDALCYCLIST        (2), 
  aPUBLICSAFETYWORKER  (3),
  anANIMAL             (4),
   aWheelchair 			(5),
   aSelfBalancingDevice	(6),
   aStandingScooter			(7), 
   aSeatedScooter			(8), 
   aSkates					(9),
   anOneWheelTransporter	(10),
   aCargoBike				(11),
   aConstructionWorker		(12),
   anOther					(13),
  ...
}

PivotingAllowed ::= BOOLEAN 

PositionConfidence ::= ENUMERATED {
  unavailable (0),  
  a500m   (1), 
  a200m   (2), 
  a100m   (3), 
  a50m    (4), 
  a20m    (5), 
  a10m    (6), 
  a5m     (7), 
  a2m     (8), 
  a1m     (9), 
  a50cm  (10), 
  a20cm  (11), 
  a10cm  (12), 
  a5cm   (13), 
  a2cm   (14), 
  a1cm   (15)  
} 

PrioritizationResponseStatus ::= ENUMERATED {
  unknown            (0),
  requested          (1),
  processing         (2),
  watchOtherTraffic  (3),
  granted            (4),
  rejected           (5),
  maxPresence        (6),
  reserviceLocked    (7),
  ...
}
  
Priority ::= OCTET STRING (SIZE(1)) 

PriorityRequestType ::= ENUMERATED {
  priorityRequestTypeReserved  (0),
  priorityRequest              (1),
  priorityRequestUpdate        (2),
  priorityCancellation         (3),
  ...
}

PrivilegedEventFlags ::= BIT STRING {
  peUnavailable                (0), 
  peEmergencyResponse          (1),
  peEmergencyLightsActive      (2),
  peEmergencySoundActive       (3),
  peNonEmergencyLightsActive   (4),
  peNonEmergencySoundActive    (5)
} (SIZE (16))

ProbeSegmentNumber ::= INTEGER (0..32767)  

PublicSafetyAndRoadWorkerActivity ::= BIT STRING {
  unavailable          (0), 
  workingOnRoad        (1), 
  settingUpClosures    (2), 
  respondingToEvents   (3), 
  directingTraffic     (4), 
  otherActivities      (5)  
} (SIZE (6, ...))

PublicSafetyDirectingTrafficSubType ::= BIT STRING {
  unavailable                              (0),
  policeAndTrafficOfficers                 (1),
  trafficControlPersons                    (2),
  railroadCrossingGuards                   (3),
  civilDefenseNationalGuardMilitaryPolice  (4),
  emergencyOrganizationPersonnel           (5),
  highwayServiceVehiclePersonnel           (6)
} (SIZE (7, ...))

PublicSafetyEventResponderWorkerType ::= ENUMERATED {
  unavailable          (0),
  towOperater          (1),
  fireAndEMSWorker     (2),
  aDOTWorker           (3),
  lawEnforcement       (4),
  hazmatResponder      (5), 
  animalControlWorker  (6),
  otherPersonnel       (7),
  ...
}

RadiusOfCurvature ::= INTEGER (-32767..32767)

Radius-B12 ::= INTEGER (0..4095)

RainSensor ::= ENUMERATED {
  none               (0), 
  lightMist          (1), 
  heavyMist          (2), 
  lightRainOrDrizzle (3),
  rain               (4),
  moderateRain       (5),
  heavyRain          (6),
  heavyDownpour      (7) 
}

RegionId ::= INTEGER (0..255)
  noRegion RegionId ::= 0 
  addGrpA RegionId ::= 1 
  addGrpB RegionId ::= 2 
  addGrpC RegionId ::= 3 
  addGrpD RegionId ::= 4 

RequestedItem ::= ENUMERATED {
  reserved,
  itemA,
  
  
  
  
  itemB,
  
  
  
  itemC,
  
  
  
  itemD,
  
  
  
  
  itemE,
  
  
  
  
  
  
  itemF,
  
  
  
  itemG,
  
  
  
  itemI,
  
  
  
  itemJ,
  
  
  
  itemK,
  
  
  
  itemL,
  
  
  
  itemM,
  
  
  
  itemN,
  
  
  
  itemO,
  
  
  
  itemP,
  
  
  
  itemQ,
  
  
  
	itemR,
  
	
	...	
}

RequestID ::= INTEGER (0..255)

RequestImportanceLevel ::= ENUMERATED {
  requestImportanceLevelUnKnown (0),
  requestImportanceLevel1       (1), 
  requestImportanceLevel2       (2), 
  requestImportanceLevel3       (3), 
  requestImportanceLevel4       (4), 
  requestImportanceLevel5       (5), 
  requestImportanceLevel6       (6),
  requestImportanceLevel7       (7),
  requestImportanceLevel8       (8),
  requestImportanceLevel9       (9),
  requestImportanceLevel10     (10),
  requestImportanceLevel11     (11),
  requestImportanceLevel12     (12),
  requestImportanceLevel13     (13),
  requestImportanceLevel14     (14),  
  requestImportanceReserved    (15)   
}

RequestSubRole ::= ENUMERATED {
  requestSubRoleUnKnown   (0),
  requestSubRole1         (1), 
  requestSubRole2         (2), 
  requestSubRole3         (3), 
  requestSubRole4         (4), 
  requestSubRole5         (5), 
  requestSubRole6         (6),
  requestSubRole7         (7),
  requestSubRole8         (8),
  requestSubRole9         (9),
  requestSubRole10       (10),
  requestSubRole11       (11),
  requestSubRole12       (12),
  requestSubRole13       (13),
  requestSubRole14       (14), 
  requestSubRoleReserved (15)  
}

ResponseType ::= ENUMERATED {
  notInUseOrNotEquipped      (0),            
  emergency                  (1),  
  nonEmergency               (2),  
  pursuit                    (3),  
  stationary                 (4),  
  slowMoving                 (5),  
  stopAndGoMovement          (6),  
  ...
} 


RestrictionAppliesTo ::= ENUMERATED {
  none                 (0),  
  equippedTransit      (1),  
  equippedTaxis        (2),
  equippedOther        (3),  
  emissionCompliant    (4), 
  equippedBicycle      (5),
  weightCompliant      (6),
  heightCompliant      (7),
  pedestrians          (8),
  slowMovingPersons    (9),
  wheelchairUsers      (10),
  visualDisabilities   (11),
  audioDisabilities    (12), 
  otherUnknownDisabilities  (13),
  ...
}

RestrictionClassID ::= INTEGER (0..255)
  
RoadRegulatorID ::= INTEGER (0..65535)

RoadSegmentID ::= INTEGER (0..65535)

RoadwayCrownAngle ::= INTEGER (-128..127)

RTCM-Revision ::= ENUMERATED {
  unknown  (0),
  rtcmRev2 (1), 
  rtcmRev3 (2), 
  reserved (3),
  ...
}
  
RTCMmessage ::= OCTET STRING (SIZE(1..1023))

Scale-B12 ::= INTEGER (-2048..2047)

SecondOfTime ::= INTEGER (0..61)

SegmentAttributeLL ::= ENUMERATED { 
  
  reserved                  ,  
  doNotBlock                , 
  whiteLine                 ,  

  
  mergingLaneLeft           , 
  mergingLaneRight          ,
  curbOnLeft                ,  
  curbOnRight               ,
  loadingzoneOnLeft         ,  
  loadingzoneOnRight        ,
  turnOutPointOnLeft        , 
  turnOutPointOnRight       ,
  adjacentParkingOnLeft     , 
  adjacentParkingOnRight    ,

  
  adjacentBikeLaneOnLeft    , 
  adjacentBikeLaneOnRight   ,
  sharedBikeLane            , 
  bikeBoxInFront            ,

  
  transitStopOnLeft         , 
  transitStopOnRight        , 
  transitStopInLane         ,
  sharedWithTrackedVehicle  ,

  
  safeIsland                , 
  lowCurbsPresent           , 
  rumbleStripPresent        , 
  audibleSignalingPresent   , 
  adaptiveTimingPresent     ,
  rfSignalRequestPresent    , 
  partialCurbIntrusion      , 
  
  
  taperToLeft               , 
  taperToRight              , 
  taperToCenterLine         , 

  
  parallelParking           , 
  headInParking             ,
  freeParking               , 
  timeRestrictionsOnParking , 
  costToPark                , 
  midBlockCurbPresent       , 
  unEvenPavementPresent     , 
  ...
}
  
SegmentAttributeXY ::= ENUMERATED {
  
  reserved                   ,
  doNotBlock                 , 
  whiteLine                  , 

  
  mergingLaneLeft            , 
  mergingLaneRight           ,
  curbOnLeft                 , 
  curbOnRight                ,
  loadingzoneOnLeft          , 
  loadingzoneOnRight         ,
  turnOutPointOnLeft         , 
  turnOutPointOnRight        ,
  adjacentParkingOnLeft      , 
  adjacentParkingOnRight     ,

  
  adjacentBikeLaneOnLeft     , 
  adjacentBikeLaneOnRight    ,
  sharedBikeLane             , 
  bikeBoxInFront             ,

  
  transitStopOnLeft          , 
  transitStopOnRight         , 
  transitStopInLane          ,  
  sharedWithTrackedVehicle   ,  

  
  safeIsland                 , 
  lowCurbsPresent            ,  
  rumbleStripPresent         ,  
  audibleSignalingPresent    ,  
  adaptiveTimingPresent      ,  
  rfSignalRequestPresent     , 
  partialCurbIntrusion       ,  

  
  taperToLeft                ,  
  taperToRight               ,  
  taperToCenterLine          , 

  
  parallelParking            , 
  headInParking              , 
  freeParking                , 
  timeRestrictionsOnParking  , 
  costToPark 								 , 
  midBlockCurbPresent 			 ,
  unEvenPavementPresent 		 , 
  ...
}
  
SemiMajorAxisAccuracy ::= INTEGER (0..255)

SemiMajorAxisOrientation ::= INTEGER (0..65535)

SemiMinorAxisAccuracy ::= INTEGER (0..255)

SignalGroupID ::= INTEGER (0..255)

SignPrority ::= INTEGER (0..7)

SirenInUse ::= ENUMERATED {
  unavailable   (0), 
  notInUse      (1),  
  inUse         (2),  
  reserved      (3)  
}

SpeedAdvice ::= INTEGER (0..500)

SpeedConfidence ::= ENUMERATED {
  unavailable (0), 
  prec100ms   (1), 
  prec10ms    (2), 
  prec5ms     (3), 
  prec1ms     (4), 
  prec0-1ms   (5), 
  prec0-05ms  (6), 
  prec0-01ms  (7)  
}

SpeedLimitType ::= ENUMERATED {
  unknown,                    
  maxSpeedInSchoolZone,       
  maxSpeedInSchoolZoneWhenChildrenArePresent, 
  maxSpeedInConstructionZone, 
  vehicleMinSpeed,
  vehicleMaxSpeed,    
  vehicleNightMaxSpeed,

  truckMinSpeed,
  truckMaxSpeed,
  truckNightMaxSpeed,

  vehiclesWithTrailersMinSpeed,
  vehiclesWithTrailersMaxSpeed,
  vehiclesWithTrailersNightMaxSpeed,
  ...
} 
  
SpeedProfileMeasurement ::= GrossSpeed 

Speed ::= INTEGER (0..8191)

SSPindex ::= INTEGER (0..31)

StabilityControlStatus ::= ENUMERATED {
  unavailable (0), 
  off         (1), 
  on          (2), 
  engaged     (3)  
}

StationID ::= INTEGER (0..4294967295)

SteeringWheelAngleConfidence ::= ENUMERATED {
  unavailable (0), 
  prec2deg    (1), 
  prec1deg    (2), 
  prec0-02deg (3)  
}
  
SteeringWheelAngleRateOfChange ::= INTEGER (-127..127) 

SteeringWheelAngle ::= INTEGER (-126..127) 

SunSensor ::= INTEGER (0..1000) 

TemporaryID ::= OCTET STRING (SIZE(4))

TermDistance ::= INTEGER (1..30000) 

TermTime ::= INTEGER (1..1800) 

ThrottleConfidence ::= ENUMERATED {
  unavailable     (0), 
  prec10percent   (1), 
  prec1percent    (2), 
  prec0-5percent  (3)  
}

ThrottlePosition ::= INTEGER (0..200)

TimeConfidence ::= ENUMERATED {
  unavailable              (0), 
  time-100-000             (1), 
  time-050-000             (2), 
  time-020-000             (3), 
  time-010-000             (4), 
  time-002-000             (5), 
  time-001-000             (6), 
  time-000-500             (7), 
  time-000-200             (8), 
  time-000-100             (9), 
  time-000-050            (10), 
  time-000-020            (11), 
  time-000-010            (12), 
  time-000-005            (13), 
  time-000-002            (14), 
  time-000-001            (15), 
  time-000-000-5          (16), 
  time-000-000-2          (17), 
  time-000-000-1          (18), 
  time-000-000-05         (19), 
  time-000-000-02         (20), 
  time-000-000-01         (21), 
  time-000-000-005        (22), 
  time-000-000-002        (23), 
  time-000-000-001        (24), 
  time-000-000-000-5      (25), 
  time-000-000-000-2      (26), 
  time-000-000-000-1      (27), 
  time-000-000-000-05     (28), 
  time-000-000-000-02     (29), 
  time-000-000-000-01     (30), 
  time-000-000-000-005    (31), 
  time-000-000-000-002    (32), 
  time-000-000-000-001    (33), 
  time-000-000-000-000-5  (34), 
  time-000-000-000-000-2  (35), 
  time-000-000-000-000-1  (36), 
  time-000-000-000-000-05 (37), 
  time-000-000-000-000-02 (38), 
  time-000-000-000-000-01 (39)  
}

TimeIntervalConfidence ::= INTEGER (0..15)

TimeMark ::= INTEGER (0..36111)

TimeOffset ::= INTEGER (1..65535)

TractionControlStatus ::= ENUMERATED {
  unavailable (0),
  off         (1),
  on          (2),
  engaged     (3) 
}

TrailerMass ::= INTEGER (0..255) 





TransitVehicleOccupancy ::= ENUMERATED {
  occupancyUnknown	(0), 
  occupancyEmpty 		(1), 
  occupancyVeryLow  (2), 
  occupancyLow 			(3), 
  occupancyMed 			(4), 
  occupancyHigh 		(5), 
  occupancyNearlyFull   (6), 
  occupancyFull 		(7)
}

TransitVehicleStatus ::= BIT STRING {
  loading    (0),  
  anADAuse   (1),  
  aBikeLoad  (2),  
  doorOpen   (3),  
  charging   (4),  
  atStopLine (5)   
} (SIZE(8))
  
TransmissionState ::= ENUMERATED {
  neutral      (0), 
  park         (1), 
  forwardGears (2), 
  reverseGears (3), 
  reserved1    (4),      
  reserved2    (5),      
  reserved3    (6),      
  unavailable  (7)  
}

TravelerInfoType ::= ENUMERATED {
  unknown	 	 				(0), 
  advisory 					(1),
  roadSignage 	 		(2), 
  commercialSignage	(3),
  ... 
}
  
UniqueMSGID ::= OCTET STRING (SIZE(9))

URL-Base ::= IA5String (SIZE(1..45))

URL-Short ::= IA5String (SIZE(1..15))

UserSizeAndBehaviour ::= BIT STRING {
  unavailable    (0),
  smallStature   (1),
  largeStature   (2),
  erraticMoving  (3),
  slowMoving     (4) 
} (SIZE (5, ...))

VehicleEventFlags ::= BIT STRING {
  eventHazardLights               (0),
  eventStopLineViolation          (1), 
  eventABSactivated               (2),
  eventTractionControlLoss        (3),
  eventStabilityControlactivated  (4),
  eventHazardousMaterials         (5),
  eventReserved1                  (6),   
  eventHardBraking                (7),
  eventLightsChanged              (8),
  eventWipersChanged              (9),
  eventFlatTire                   (10),
  eventDisabledVehicle            (11), 
  eventAirBagDeployment           (12)
} (SIZE (13, ...))

VehicleHeight ::= INTEGER (0..127) 


VehicleLength ::= INTEGER (0.. 4095) 

VehicleMass ::= INTEGER (0..255)


VehicleStatusDeviceTypeTag ::= ENUMERATED {
  unknown            (0),
  lights             (1),  
  wipers             (2),  
  brakes             (3),  
  stab               (4),  
  trac               (5),  
  abs                (6),  
  sunS               (7),  
  rainS              (8),  
  airTemp            (9),  
  steering           (10),
  vertAccelThres     (11), 
  vertAccel          (12), 
  hozAccelLong       (13), 
  hozAccelLat        (14), 
  hozAccelCon        (15), 
  accel4way          (16),
  confidenceSet      (17),
  obDist             (18), 
  obDirect           (19), 
  yaw                (20), 
  yawRateCon         (21), 
  dateTime           (22), 
  fullPos            (23), 
  position2D         (24), 
  position3D         (25), 
  vehicle            (26), 
  speedHeadC         (27), 
  speedC             (28),
  ...  
}
  
VehicleType ::= ENUMERATED {
  none                 (0),  
  unknown              (1),  
  special              (2),  
  moto                 (3),  
  car                  (4),  
  carOther             (5),  
  bus                  (6),  
  axleCnt2             (7),  
  axleCnt3             (8),  
  axleCnt4             (9),  
  axleCnt4Trailer      (10), 
  axleCnt5Trailer      (11), 
  axleCnt6Trailer      (12), 
  axleCnt5MultiTrailer (13), 
  axleCnt6MultiTrailer (14), 
  axleCnt7MultiTrailer (15),  
  ...  
} 

VehicleWidth ::= INTEGER (0..1023) 

Velocity ::= INTEGER (0..8191) 


VerticalAccelerationThreshold ::= BIT STRING {
  notEquipped (0), 
  leftFront   (1), 
  leftRear    (2), 
  rightFront  (3), 
  rightRear   (4)  
} (SIZE(5))

VerticalAcceleration ::= INTEGER (-127..127) 

VertOffset-B07 ::= INTEGER (-64..63)  






VertOffset-B12 ::= INTEGER (-2048..2047)  

VINstring ::= OCTET STRING (SIZE(1..17)) 

WaitOnStopline ::= BOOLEAN 

WiperRate ::= INTEGER (0..127)

WiperStatus ::= ENUMERATED {
  unavailable         (0),
  off                 (1),  
  intermittent        (2), 
  low                 (3),
  high                (4),
  washerInUse         (5),
  automaticPresent    (6),
  ...  
}

YawRateConfidence ::= ENUMERATED {
  unavailable    (0), 
  degSec-100-00  (1), 
  degSec-010-00  (2), 
  degSec-005-00  (3), 
  degSec-001-00  (4), 
  degSec-000-10  (5), 
  degSec-000-05  (6), 
  degSec-000-01  (7)  
}  
  
YawRate ::= INTEGER (-32767..32767) 

ZoneLength ::= INTEGER (0..10000)

Zoom ::= INTEGER (0..15)

ConsecutiveTrafficLight-KOR ::= INTEGER(0..15)
  none		ConsecutiveTrafficLight-KOR::= 0
  first		ConsecutiveTrafficLight-KOR::= 1
  second	ConsecutiveTrafficLight-KOR::= 2

ReservedBit-KOR ::= BOOLEAN

ActuatedInterval-KOR ::= BOOLEAN

ADASEventType-KOR ::= ENUMERATED {
  nowarning   (0), 
  bus		  (1),
  car		  (2),
  truck		  (3),
  motors      (4),
  special     (5),
  bicycle     (6),
  pedestrian  (7),
  pothole     (8),
  rubbercon	  (9),
  ldwsLeft	  (10),
  ldwsRight	  (11),
  ldwsWarning (12),
  ...
}

BasicVehicleClass-KOR ::= ENUMERATED {
  unknown 				              (0),
  passenger-vehicle-tiny        (1),
  passenger-vehicle-mini 	      (2),
  passenger-vehicle-small       (3),	
  passenger-vehicle-medium      (4),	
  passenger-vehicle-fullsize    (5),	
  van-mini 				              (6),	
  van-small 			  	          (7),	
  van-medium 			              (8),	
  van-fullsize 			            (9),	
  truck-tiny 			              (10),	
  truck-mini 			              (11),	
  truck-small-A 		            (12),	
  truck-small-B 		            (13),	
  truck-medium-A 			          (14),	
  truck-medium-B 			          (15),	
  truck-medium-C 			          (16),	
  truck-fullsize-A  		        (17),	
  truck-fullsize-B  	        	(18),	
  truck-fullsize-C  		        (19),	
  truck-fullsize-D  	        	(20),	
  truck-fullsize-E  		        (21),	
  special-vehicle-mini 	        (22),	
  special-vehicle-small         (23),	
  special-vehicle-medium 	      (24),	
  special-vehicle-fullsize      (25),	
  motorcycle-mini 		          (26),	
  motorcycle-small 		          (27),	
  motorcycle-medium 	          (28),	
  motorcycle-fullsize 	        (29),	
  heavy-equipment 		          (30),	
  motorcycle-tiny 		          (31),	
  motorized-bicycle 		        (32),	
  personal-mobility-kickboard   (33),   
  personal-mobility-segway      (34),   
  personal-mobility-throttle-bicycle  (35),   
  bicycle-general 			        (36),	
  bicycle-pas 			            (37),	
  horse-cattle 			            (38),	
  tram 				                  (39),	
  pedestrian 			              (40),	
  etc 				                  (41)	
}

BasicVehicleRole-KOR ::= ENUMERATED {
  unknown 			 	          (0),	
  general-passenger-vehicle (1),	
  general-school-bus 		    (2),	
  general-bicycle 			    (3),	
  general-motorcycle 		    (4),	
  general-heavy-equipment 	(5),	
  general-vehicle-with-trailer   (6), 	
  general-pedestrian 			  (7),	    
  general-personal-mobility (8),	
  general-farming-vehicle 	(9),  	
  general-recreational-vehicle   (10),	
  general-etc 		 	        (11),	
  general-unknown 	 		    (12),	
  emergency-police 	 		    (13),	
  emergency-fire 	 		      (14),	
  emergency-ambulance 		  (15),	
  emergency-hazmat 			    (16),	
  emergency-military 		    (17),	
  emergency-prosecutor 		  (18),	
  emergency-prison 	 		    (19),	
  emergency-gov-affairs 		(20),	
  emergency-pub-affairs 		(21),		
  emergency-civil-defense 	(22),
  emergency-post 	 			  (23),
  emerency-etc 	 			    (24),
  public-transport-bus 		(25),
  public-transport-taxi 	(26),
  public-transport-tram 	(27),
  roadmgmt-construction-vehicle  (28),
  roadmgmt-snow-plow      (29),
  roadmgmt-brush-vehicle 	(30),
  roadmgmt-road-rescue 		(31),
  truck 					        (32),
  oversize-truck 				  (33),
  overweight-truck 			  (34)
}

BrakePedalPressure-KOR ::= INTEGER (0..101)

BrakePedalCmd-KOR ::= ENUMERATED {
  off		(0),
  on		(1)
}

DectLane-KOR ::= ENUMERATED {
  unavailable		(0),
  busOnlyLane		(10),
  ctrBusLane		(11),
  rdSdBusLane		(12),
  mergingLane		(13),
  accelerationLane	(14),
  decelrationLane	(15),
  rampLane			(16),
  shoulderLane		(17),
  carLane			(20),
  car-1stLane		(21),
  car-2ndLane		(22),
  car-3rdLane		(23),
  car-4thLane		(24),
  car-5thLane		(25),
  car-6thLane		(26),
  car-7thLane		(27),
  car-8thLane		(28),
  car-9thLane		(29),
  car-10thLane		(30),
  car-11thLane		(31),
  car-12thLane		(32),
  car-13thLane		(33),
  car-14thLane		(34),
  car-15thLane		(35),
  car-16thLane		(36),
  car-17thLane		(37),
  car-18thLane		(38),
  car-19thLane		(39),
  car-20thLane		(40),
  etcLane			(99),
  ...
}

DeviceStatus-KOR ::= BIT STRING {
  noADASignal	 		(0), 
  noDrowsySignal	(1),
  noV2XSignal			(2),
  noDisplaySignal (3),
  noDTGSignal	 		(4),
  noGPSignal	    (5),
  noCITSCenterCon	(6),
  noHMIstate	 		(7)
} (SIZE (8))

Disabled-KOR ::= BOOLEAN

DrivingStatus-KOR ::= ENUMERATED {	
  stop						(0),
  forward-moving	(1),
  backward-moving	(2),
  straight				(3),
  left-turning		(4),
  right-turning		(5),
  parking					(6),
  ...
}

FuelType-KOR ::= ENUMERATED {
  gasoline				(0),
  diesel 					(1),
  lpg							(2),
  premium					(3),
  hydrogen				(4),
  normalCharging	(5),
  quickCharging		(6),
  supercharging		(7),
  ...
}

HighwayDirection-KOR ::= ENUMERATED {
  up 				(0),
  down			(1),
  upAndDown	(2),
  ...
}

HumanDriverStatus-KOR ::= ENUMERATED {
  frontEyeOut 	(0), 
  drowsyLight		(1),
  drowsySerious	(2),
  faceOut     	(3),
  smoking 	    (4),
  phone	 	    	(5),
  yawn	 	    	(6),
  ...
}

ITISCodes-KOR ::= INTEGER (0..65535)
  weather-conditions			        ITISCodes-KOR ::=    18  
  stop-and-go-traffic			        ITISCodes-KOR ::=   258  
  lon-queues 					        ITISCodes-KOR ::=   262  
  speed-limit					        ITISCodes-KOR ::=   268  
  accident 						        ITISCodes-KOR ::=   513  
  disabled-vehicle 			            ITISCodes-KOR ::=   534  
  vehicle-on-fire 				        ITISCodes-KOR ::=   540  
  accident-cleared		    	        ITISCodes-KOR ::=   638  
  incident-cleared 		    	        ITISCodes-KOR ::=   639  
  closed-to-traffic		    	        ITISCodes-KOR ::=   769  
  road-construction		    	        ITISCodes-KOR ::=  1025  
  road-maintenance-cleared    	        ITISCodes-KOR ::=  1036  
  obstruction-on-roadway		        ITISCodes-KOR ::=  1281  
  people-on-roadway			            ITISCodes-KOR ::=  1286  
  pothole						        ITISCodes-KOR ::=  1300  
  flooding		   				        ITISCodes-KOR ::=  1301  
  landslide					            ITISCodes-KOR ::=  1310  
  clearance-work				        ITISCodes-KOR ::=  1406  
  obstruction-cleared			        ITISCodes-KOR ::=  1407  
  vehicle-traveling-wrong-way	        ITISCodes-KOR ::=  1793 
  emergency-vehicles-on-roadway      	ITISCodes-KOR ::=  1796 
  dangerous-vehicle-warning-cleared		ITISCodes-KOR ::=  1918 
  slow-vehicle		        		    ITISCodes-KOR ::=  2052 
  variable-message-signs-not-working	ITISCodes-KOR ::=  2308 
  variable-message-signs-operating 		ITISCodes-KOR ::=  2310 
  bus-lane-available-for-all-vehicles	ITISCodes-KOR ::=  2583 
  earthquake-damage			            ITISCodes-KOR ::=  3093 
  emergency-stopping-only	            ITISCodes-KOR ::=  4119 
  parking 						        ITISCodes-KOR ::=  4120 
  stopping						        ITISCodes-KOR ::=  4121 
  heavy-snow					        ITISCodes-KOR ::=  4867 
  hail							        ITISCodes-KOR ::=  4880 
  heavy-rain 					        ITISCodes-KOR ::=  4884 
  tropical-storm				        ITISCodes-KOR ::=  5124 
  strong-winds					        ITISCodes-KOR ::=  5125 
  dense-fog 					        ITISCodes-KOR ::=  5377 
  air-quality-good 			            ITISCodes-KOR ::=  5394 
  air-quality-fair 		    	        ITISCodes-KOR ::=  5395 
  air-quality-poor 		    	        ITISCodes-KOR ::=  5396 
  air-quality-very-poor		            ITISCodes-KOR ::=  5397 
  surface-water-hazard		            ITISCodes-KOR ::=  5893 
  wet-pavement 		    		        ITISCodes-KOR ::=  5895 
  black-ice 					        ITISCodes-KOR ::=  5908 
  snow-on-roadway				        ITISCodes-KOR ::=  5916 
  increased-risk-of-accident	        ITISCodes-KOR ::=  6922 
  use-shoulder-as-lane 		            ITISCodes-KOR ::=  7436 
  do-not-drive-on-the-shoulder	        ITISCodes-KOR ::=  7437 
  reduce-your-speed			            ITISCodes-KOR ::=  7443 
  u-turn			    		        ITISCodes-KOR ::=  7751 
  in-tunnels					        ITISCodes-KOR ::=  7983 
  service-area					        ITISCodes-KOR ::=  7984 
  shoulder						        ITISCodes-KOR ::=  8027 
  toll-plaza					        ITISCodes-KOR ::=  8215 
  bus-lanes 					        ITISCodes-KOR ::=  8220 
  traffic			   		 	        ITISCodes-KOR ::=  9261 
  pedestrians 					        ITISCodes-KOR ::=  9486 
  bicyclists 					        ITISCodes-KOR ::=  9487 
  county-police-units 		            ITISCodes-KOR ::=  9732 
  ambulance-units 				        ITISCodes-KOR ::=  9734 
  fire-units 					        ITISCodes-KOR ::=  9736 
  hAZMAT-units					        ITISCodes-KOR ::=  9737 
  brush-truck 					        ITISCodes-KOR ::= 10000 
  construction-vehicle 		            ITISCodes-KOR ::= 10088 
  snowplow 						        ITISCodes-KOR ::= 10102 
  cones			    			        ITISCodes-KOR ::= 10504 
  fixed-VMS					            ITISCodes-KOR ::= 10537 
  emergency-signal			            ITISCodes-KOR ::= 10570 
  junction						        ITISCodes-KOR ::= 13378 
  ahead 			    		        ITISCodes-KOR ::= 13569 
  left-turn					            ITISCodes-KOR ::= 13594 
  right-turn					        ITISCodes-KOR ::= 13599 
  

MsgChannel-KOR ::= INTEGER (0..65535)

MsgCommType-KOR ::= ENUMERATED {
  unavailable 	(0),
	wave			(1),
	lte-4G			(2),
	lte-5G			(3),
	lte-v2x-rel14	(4),
	lte-v2x-rel15	(5),
	lte-v2x-rel16	(6),
	lte-v2x-rel17	(7),
	lte-v2x-rel18	(8),
	lte-v2x-rel19	(9),
	lte-v2x-rel20	(10),
  ...
}

MsgDeviceType-KOR ::= ENUMERATED {
  other			(0),
  communication	(1),
  display		(2), 
  adas 			(3),
  drowsinessDetector	(4),
  ...
}

MsgDisplayLocation-KOR ::= INTEGER (0..128)
  entry								MsgDisplayLocation-KOR ::= 0    
  beforeEntry					MsgDisplayLocation-KOR ::= 1    
  timIn								MsgDisplayLocation-KOR ::= 2    
  timOut							MsgDisplayLocation-KOR ::= 3    
  ttcZone0						MsgDisplayLocation-KOR ::= 4    
  ttcZone1						MsgDisplayLocation-KOR ::= 5    
  ttcZone2						MsgDisplayLocation-KOR ::= 6    
  ttcZone3						MsgDisplayLocation-KOR ::= 7    
  alertZone        		MsgDisplayLocation-KOR ::= 8    
  v2vPreapproachZone0 MsgDisplayLocation-KOR ::= 9  
  v2vApproachZone0  	MsgDisplayLocation-KOR ::= 10   
  v2vApproachZone1  	MsgDisplayLocation-KOR ::= 11   
  others            	MsgDisplayLocation-KOR ::= 12   
  
MsgType-KOR ::= ENUMERATED {
  bsm						(0),
  spat					(1),
  tls						(2),
  map						(3),
  nmeacorrection	(4),
  rtcmcorrection	(5),
  pvd						(6),
  pdm						(7),
  rsa						(8),
  tim						(9),
  adas					(10),
  psm						(11),
  drowsiness		(12),
  ...
}

ParkingType-KOR ::= ENUMERATED {
  normal 		(0),
  disable		(1),
  big				(2),
  compact		(3),
  emergency	(4),
  women			(5),
  etc				(6),
  ...
}

PedestrianCall-KOR ::= BOOLEAN

PermissiveNonProtected-KOR ::= BOOLEAN

PossibleTurn-KOR ::= ENUMERATED {
  none				(0),
  left-turn		(1),
  right-turn	(2),
  both-turn		(3),
  ... 
}

ResponseType-KOR ::= ENUMERATED {
  not-in-use						(0), 
  emergency							(1), 
  non-emergency					(2), 
  emergency-in-drill 		(3), 
  emergency-pursuit 		(4), 
  emergency-stationary 	(5), 
  emergency-slow-moving	(6), 
  emergency-stop-go			(7),
  ...
}

Rpm-KOR ::= INTEGER (0..16383)

TimeInSecond-B16-KOR ::= INTEGER (0..65535)

TimeInSecond-B8-KOR ::= INTEGER (0..255)

TollgateType-KOR ::= ENUMERATED {
  general	 	 	(1), 
  hipass 			(2),
  truck-hipass 	 	(3), 
  multi-hipass-2	(4),
  multi-hipass-3	(5),
  multi-hipass-4	(6),
  multi-hipass-5	(7),
  multi-hipass-6	(8),
  multi-hipass-7	(9),
  multi-hipass-8	(10),
  multi-hipass-9	(11),
  multi-hipass-10	(12),
  ... 
}

TrafficLightControllerStatus-KOR ::= BIT STRING {
  conflict 			  (0), 
  center-comm-error   (1), 
  scu-comm-error	  (2), 
  reserved1			  (3), 
  reserved2			  (4), 
  reserved3			  (5),
  reserved4			  (6),
  reserved5           (7)
} (SIZE(8))

TrafficLightDirectionCode-KOR ::= INTEGER(10..89)
  north	 	    TrafficLightDirectionCode-KOR    ::= 10
  east	      TrafficLightDirectionCode-KOR    ::= 20
  south		    TrafficLightDirectionCode-KOR    ::= 30
  west 	      TrafficLightDirectionCode-KOR    ::= 40
  northeast	  TrafficLightDirectionCode-KOR    ::= 50
  southeast 	TrafficLightDirectionCode-KOR    ::= 60
  southwest   TrafficLightDirectionCode-KOR    ::= 70
  northwest   TrafficLightDirectionCode-KOR    ::= 80
TrafficLightID-KOR ::= INTEGER(0..4294967295)

TrafficLightingStatus-KOR ::= INTEGER(0..10)
  off             TrafficLightingStatus-KOR    ::= 0
  red-on          TrafficLightingStatus-KOR    ::= 1
  yellow-on       TrafficLightingStatus-KOR    ::= 2
  green-on        TrafficLightingStatus-KOR    ::= 3
  red-blinking    TrafficLightingStatus-KOR    ::= 4
  yellow-blinking	TrafficLightingStatus-KOR    ::= 5
  green-blinking	TrafficLightingStatus-KOR    ::= 6
  
TrafficLightIntervalType-KOR ::= ENUMERATED {
  static   (0),
  variable (1),
  ...
}

TrafficLightOperationStatus-KOR ::= BIT STRING {
  manual 		  	(0), 
  flashing 		  (1), 
  off 			  	(2), 
  actuted 		  (3), 
  transition 	  (4), 
  priority 		  (5),
  holding-phase (6),
  reserved 		  (7)
} (SIZE(8))

TrafficLightStatusCount-KOR ::= INTEGER (0..255)

TrafficLightType-KOR ::= INTEGER(0..15)
  reserved		TrafficLightType-KOR  ::= 0
  straight	  TrafficLightType-KOR  ::= 1
  leftTurn		TrafficLightType-KOR  ::= 2
  pedestrian 	TrafficLightType-KOR  ::= 3
  bicycle 	  TrafficLightType-KOR  ::= 4
  rightTurn 	TrafficLightType-KOR 	::= 5
  bus        	TrafficLightType-KOR	::= 6
  uTurn      TrafficLightType-KOR	::= 7
  
VehicleControlMode-KOR ::= ENUMERATED {
  manual	(0),
  auto		(1),
  ...
}

VehicleEventFlags-KOR ::= BIT STRING {
  airbagOpening		      (0), 
  tireAirPressureError  (1), 
  batteryDischarge		  (2), 
  highTemperature 		  (3), 
  exteriorLightsAbnormal  (4), 
  otherEvents		      (5), 
  wiperChange		      (6), 
  reserved			      (7)  
} (SIZE(8))

VerticalHeading-KOR ::= INTEGER(-101..100)

EssMobileFriction ::= INTEGER (0..101)

EssPrecipRate ::= INTEGER (0..65535) 
  
EssPrecipSituation ::= ENUMERATED {
  other (1), 
  unknown (2), 
  noPrecipitation (3), 
  unidentifiedSlight (4), 
  unidentifiedModerate (5), 
  unidentifiedHeavy (6), 
  snowSlight (7), 
  snowModerate (8), 
  snowHeavy (9), 
  rainSlight (10), 
  rainModerate (11), 
  rainHeavy (12), 
  frozenPrecipitationSlight (13), 
  frozenPrecipitationModerate (14), 
  frozenPrecipitationHeavy (15)
}

EssPrecipYesNo ::= ENUMERATED {precip (1), noPrecip (2), error (3)} 

EssSolarRadiation ::= INTEGER (0..65535) 

GenericLocations ::= ENUMERATED  { 
  on-bridges                  (7937),  
  in-tunnels                  (7938),  
  entering-or-leaving-tunnels (7939),  
  on-ramps                    (7940),  
  in-road-construction-area   (7941),  
  around-a-curve              (7942),  
  on-curve                    (8026),   
  on-tracks                   (8009),   
  in-street                   (8025),  
  shoulder                    (8027),   
  on-minor-roads              (7943),  
  in-the-opposing-lanes       (7944),  
  adjacent-to-roadway         (7945),  
  across-tracks               (8024),   
  on-bend                     (7946),  
  intersection                (8032),   
  entire-intersection         (7947),  
  in-the-median               (7948),  
  moved-to-side-of-road       (7949),  
  moved-to-shoulder           (7950),  
  on-the-roadway              (7951),  
  dip                         (8010),   
  traffic-circle              (8011),  
  crossover                   (8028),  
  cross-road                  (8029),  
  side-road                   (8030),  
  to                          (8014),   
  by                          (8015),   
  through                     (8016),   
  area-of                     (8017),  
  under                       (8018),     
  over                        (8019),   
  from                        (8020),   
  approaching                 (8021),   
  entering-at                 (8022),  
  exiting-at                  (8023),  
  in-shaded-areas             (7952),  
  in-low-lying-areas          (7953),  
  in-the-downtown-area        (7954),  
  in-the-inner-city-area      (7955),  
  in-parts                    (7956),  
  in-some-places              (7957),  
  in-the-ditch                (7958),  
  in-the-valley               (7959),  
  on-hill-top                 (7960),  
  near-the-foothills          (7961),  
  at-high-altitudes           (7962),  
  near-the-lake               (7963),  
  near-the-shore              (7964),  
  nearby-basin                (8008),  
  over-the-crest-of-a-hill    (7965),  
  other-than-on-the-roadway   (7966),  
  near-the-beach              (7967),  
  near-beach-access-point     (7968),  
  mountain-pass               (8006),  
  lower-level                 (7969),  
  upper-level                 (7970),  
  airport                     (7971),  
  concourse                   (7972),  
  gate                        (7973),  
  baggage-claim               (7974),  
  customs-point               (7975),  
  reservation-center          (8007),  
  station                     (7976),  
  platform                    (7977),  
  dock                        (7978),  
  depot                       (7979),  
  ev-charging-point           (7980),  
  information-welcome-point   (7981),  
  at-rest-area                (7982),  
  at-service-area             (7983),  
  at-weigh-station            (7984),  
  roadside-park               (8033),  
  picnic-areas                (7985),  
  rest-area                   (7986),  
  service-stations            (7987),  
  toilets                     (7988),  
  bus-stop                    (8031),  
  park-and-ride-lot           (8012),  
  on-the-right                (7989),  
  on-the-left                 (7990),  
  in-the-center               (7991),  
  in-the-opposite-direction   (7992),  
  cross-traffic               (7993),  
  northbound-traffic          (7994),  
  eastbound-traffic           (7995),  
  southbound-traffic          (7996),  
  westbound-traffic           (7997),  
  
  north                       (7998),  
  south                       (7999),  
  east                        (8000),  
  west                        (8001),  
  northeast                   (8002),  
  northwest                   (8003),  
  southeast                   (8004),  
  southwest                   (8005),  
  ... 
}


IncidentResponseEquipment ::= ENUMERATED {
  ground-fire-suppression (9985),
  heavy-ground-equipment (9986),
  aircraft (9988),
  marine-equipment (9989),
  support-equipment (9990),
  medical-rescue-unit (9991),
  other (9993),                           
  ground-fire-suppression-other (9994),
  engine (9995),
  truck-or-aerial (9996),
  quint (9997),                           
  tanker-pumper-combination (9998),
  brush-truck (10000),
  aircraft-rescue-firefighting (10001),
  heavy-ground-equipment-other (10004),
  dozer-or-plow (10005),
  tractor (10006),
  tanker-or-tender (10008),
  aircraft-other (10024),
  aircraft-fixed-wing-tanker (10025),
  helitanker (10026),
  helicopter (10027),
  marine-equipment-other (10034),
  fire-boat-with-pump (10035),
  boat-no-pump (10036),
  support-apparatus-other (10044),
  breathing-apparatus-support (10045),
  light-and-air-unit (10046),
  medical-rescue-unit-other (10054),
  rescue-unit (10055),
  urban-search-rescue-unit (10056),
  high-angle-rescue (10057),
  crash-fire-rescue (10058),
  bLS-unit (10059),
  aLS-unit (10060),
  mobile-command-post (10075),            
  chief-officer-car (10076),
  hAZMAT-unit (10077),
  type-i-hand-crew (10078),
  type-ii-hand-crew (10079),
  privately-owned-vehicle (10083),        
  other-apparatus-resource (10084),       
  ambulance (10085),
  bomb-squad-van (10086),
  combine-harvester (10087),
  construction-vehicle (10088),
  farm-tractor (10089),
  grass-cutting-machines (10090),
  hAZMAT-containment-tow (10091),
  heavy-tow (10092),
  light-tow (10094),
  flatbed-tow (10114),
  hedge-cutting-machines (10093),
  mobile-crane (10095),
  refuse-collection-vehicle (10096),
  resurfacing-vehicle (10097),
  road-sweeper (10098),
  roadside-litter-collection-crews (10099),
  salvage-vehicle (10100),
  sand-truck (10101),
  snowplow (10102),
  steam-roller (10103),
  swat-team-van (10104),
  track-laying-vehicle (10105),
  unknown-vehicle (10106),
  white-lining-vehicle (10107),  
  dump-truck (10108),
  supervisor-vehicle (10109),
  snow-blower (10110),
  rotary-snow-blower (10111),
  road-grader (10112),            
  steam-truck (10113),            
  ... 
}

ITIStext ::= IA5String (SIZE(1..500))

ResponderGroupAffected ::= ENUMERATED {
  emergency-vehicle-units (9729), 
  federal-law-enforcement-units (9730),
  state-police-units (9731),
  county-police-units (9732),
  local-police-units (9733),
  ambulance-units (9734),
  rescue-units (9735),
  fire-units (9736),
  hAZMAT-units (9737),
  light-tow-unit (9738),
  heavy-tow-unit (9739),
  freeway-service-patrols (9740),
  transportation-response-units (9741),
  private-contractor-response-units (9742),
  ... 
  }
  
VehicleGroupAffected ::= ENUMERATED {
  all-vehicles 								(9217),
  bicycles 									(9218),
  motorcycles 								(9219), 
  cars 										(9220),        
  light-vehicles 							(9221),
  cars-and-light-vehicles 					(9222),
  cars-with-trailers 						(9223),
  cars-with-recreational-trailers 			(9224),
  vehicles-with-trailers 					(9225),
  heavy-vehicles 							(9226),
  trucks 									(9227),
  buses 									(9228),
  articulated-buses 						(9229),
  school-buses 								(9230),
  vehicles-with-semi-trailers 				(9231),
  vehicles-with-double-trailers 				(9232), 
  high-profile-vehicles 						(9233),
  wide-vehicles 								(9234),
  lon-vehicles 								(9235),
  hazardous-loads 								(9236),
  exceptional-loads 							(9237),
  abnormal-loads 								(9238),
  convoys 										(9239),
  maintenance-vehicles 							(9240),
  delivery-vehicles 							(9241),
  vehicles-with-even-numbered-license-plates 	(9242),
  vehicles-with-odd-numbered-license-plates 	(9243),
  vehicles-with-parking-permits 				(9244),
  vehicles-with-catalytic-converters 			(9245),
  vehicles-without-catalytic-converters 		(9246),
  gas-powered-vehicles 							(9247),
  diesel-powered-vehicles 						(9248),
  lPG-vehicles 									(9249),
  military-convoys 								(9250),
  military-vehicles 							(9251),
  ... 
}

ITIScodes ::= INTEGER (0..65535)

-- Legacy-only definitions retained for existing consumers.
ADASEventType ::= ENUMERATED {

   nowarning   (0),

   bus         (1),

   car         (2),

   truck       (3),

   motors      (4),

   special     (5),

   bicycle     (6),

   pedestrian  (7),

   pothole     (8),

   rubbercon   (9),

   ldwsLeft    (10),

   ldwsRight   (11),

   ldwsWarning (12),

   ...

}


VertOffset-B08 ::= INTEGER (-128..127)  

   
   
   
   
   



VertOffset-B09 ::= INTEGER (-256..255)  

   
   
   
   
   



VertOffset-B10 ::= INTEGER (-512..511)  

   
   
   
   
   



VertOffset-B11 ::= INTEGER (-1024..1023)  

   
   
   
   
   



ActuatedInterval ::= BOOLEAN




ConsecutiveTrafficLight ::= ENUMERATED {

    none    (0),

    first   (1),

    second  (2),

    ...

}




PedestrianCall ::= BOOLEAN 


PermissiveNonProtected ::= ENUMERATED {

    none        (0),  
    permissive  (1),  
    ...

}


ReservedBit ::= BOOLEAN


TimeInSecond-B16 ::= INTEGER (0..65535)




TimeInSecond-B8 ::= INTEGER (0..255)


TrafficLightControllerStatus ::= BIT STRING {

    conflict            (0), 

    
    
    
    
    center-comm-error   (1), 

    
    
    
    
    scu-comm-error      (2), 

    
    
    
    
    
    
    reserved1           (3), 

    
    reserved2           (4), 

    reserved3           (5),

    reserved4           (6),

    reserved5           (7)

} (SIZE(8, ...))


TrafficLightDirectionCode ::= INTEGER (0..359) 

TrafficLightingStatus ::= ENUMERATED {

    off             (0),

    red-on          (1),

    yellow-on       (2),

    green-on        (3),

    red-blinking    (4),

    yellow-blinking (5),

    green-blinking  (6),

    ...

}


TrafficLightIntervalType ::= ENUMERATED {

    static      (0),  
    variable    (1),  
    ...

}


TrafficLightOperationStatus ::= BIT STRING {

    manual          (0),

    
    flashing        (1),

    
    off             (2),

    
    
    
    actuated        (3),

    
    
    transition      (4),

    
    
    priority        (5),

    
    
    holding-phase   (6),

    
    
    reserved        (7)

    
} (SIZE(8, ...))


TrafficLightType ::= ENUMERATED {

    reserved        (0),

    straight        (1),

    left-turn       (2),

    pedestrian      (3),

    bicycle         (4),

    right-turn      (5),

    bus             (6),

    u-turn          (7),

    ...

}




MsgId ::= INTEGER (0..65535) 



TerminationDistance ::= INTEGER (1..30000)   

TerminationTime ::= INTEGER (1..1800) 

SignPriority ::= INTEGER (0..7)

   

ObjectDistance ::=INTEGER(-32767..32767) 



ObjectType::= ENUMERATED{

    unknown (0),

    vehicle (1),

    vru     (2),

    animal  (3),

    ...

}


ClassificationConfidence ::= INTEGER (0..101)




ObjectID ::= INTEGER (0..65535)




MeasurementTimeOffset ::= INTEGER (-1500..1500) 



PitchDetected ::= INTEGER (-7200..7200)

    
    



RollDetected ::= INTEGER (-14400..14400)

    
    



YawDetected ::= INTEGER (-14400..14400)

    
    



PitchRate ::= INTEGER (-32767..32767)

    
    



RollRate ::= INTEGER (-32767..32767)

    
    



PitchRateConfidence ::= ENUMERATED {

    unavailable (0), 
    
    degSec-100-00 (1), 
    degSec-010-00 (2), 
    degSec-005-00 (3), 
    degSec-001-00 (4), 
    degSec-000-10 (5), 
    degSec-000-05 (6), 
    degSec-000-01 (7)  
}




RollRateConfidence ::= ENUMERATED {

    unavailable (0), 
    
    degSec-100-00 (1), 
    degSec-010-00 (2), 
    degSec-005-00 (3), 
    degSec-001-00 (4), 
    degSec-000-10 (5), 
    degSec-000-05 (6), 
    degSec-000-01 (7)  
}




SizeValueConfidence ::= ENUMERATED {

    unavailable (0),

    size-100-00 (1),    
    size-050-00 (2),    
    size-020-00 (3),    
    size-010-00 (4),    
    size-005-00 (5),    
    size-002-00 (6),    
    size-001-00 (7),    
    size-000-50 (8),    
    size-000-20 (9),    
    size-000-10 (10),   
    size-000-05 (11),   
    size-000-02 (12),   
    size-000-01 (13)    
}




EquipmentType ::= ENUMERATED{

    unknown (0),

    rsu     (1),

    obu     (2),

    vru     (3),

    ...

}




SizeValue ::= INTEGER (0..1023) 




MessageFrame ::= SEQUENCE {
  messageId 	        MESSAGE-ID-AND-TYPE.&id({MessageTypes}),
  value       			MESSAGE-ID-AND-TYPE.&Type({MessageTypes}{@.messageId}),
  ...
}

MESSAGE-ID-AND-TYPE ::= CLASS {
  &id    					DSRCmsgID UNIQUE,
  &Type
} WITH SYNTAX {&Type IDENTIFIED BY &id}

MessageTypes MESSAGE-ID-AND-TYPE ::= { 
  { BasicSafetyMessage  	IDENTIFIED BY basicSafetyMessage } | 
  { MapData 		  		IDENTIFIED BY mapData } | 
  { SPAT 			  			IDENTIFIED BY signalPhaseAndTimingMessage } | 
  { CommonSafetyRequest IDENTIFIED BY commonSafetyRequest } | 
  { EmergencyVehicleAlert IDENTIFIED BY emergencyVehicleAlert } |  
  { IntersectionCollision IDENTIFIED BY intersectionCollision } |
  { NMEAcorrections   IDENTIFIED BY nmeaCorrections } |
  { ProbeDataManagement    IDENTIFIED BY probeDataManagement } |
  { ProbeVehicleData       IDENTIFIED BY probeVehicleData } | 
  { RoadSideAlert         IDENTIFIED BY roadSideAlert         } |      
  { RTCMcorrections   IDENTIFIED BY rtcmCorrections } | 
  { TravelerInformation   IDENTIFIED BY travelerInformation   } |
  { PersonalSafetyMessage IDENTIFIED BY personalSafetyMessage } |
  { TrafficLightStatusMessage IDENTIFIED BY trafficLightStatusMessage },
  ... 
}



REG-EXT-ID-AND-TYPE ::= CLASS {
  &id     RegionId UNIQUE,
  &Type
} WITH SYNTAX {&Type IDENTIFIED BY &id}

RegionalExtension {REG-EXT-ID-AND-TYPE : Set} ::= SEQUENCE {
  regionId 		REG-EXT-ID-AND-TYPE.&id( {Set} ),
  regExtValue 	REG-EXT-ID-AND-TYPE.&Type( {Set}{@regionId} )
}

BasicSafetyMessage ::= SEQUENCE {
  
  coreData      BSMcoreData,   
  
   partII        SEQUENCE (SIZE(1..8)) OF 
                 PartIIcontent {{ BSMpartIIExtension }} OPTIONAL,
   
   regional      SEQUENCE (SIZE(1..4)) OF 
                 RegionalExtension {{Reg-BasicSafetyMessage}} OPTIONAL,
  ...
}


PARTII-EXT-ID-AND-TYPE ::= CLASS {
  &id     PartII-Id UNIQUE,
  &Type
} WITH SYNTAX {&Type IDENTIFIED BY &id}

PartIIcontent  { PARTII-EXT-ID-AND-TYPE: Set} ::= SEQUENCE {
  partII-Id     PARTII-EXT-ID-AND-TYPE.&id( {Set} ),
  partII-Value  PARTII-EXT-ID-AND-TYPE.&Type( {Set}{@partII-Id} )
}

BSMpartIIExtension  PARTII-EXT-ID-AND-TYPE ::= { 
  { VehicleSafetyExtensions       IDENTIFIED BY vehicleSafetyExt} |
  { SpecialVehicleExtensions      IDENTIFIED BY specialVehicleExt} |
  { SupplementalVehicleExtensions IDENTIFIED BY supplementalVehicleExt} ,
  ... 
}

CommonSafetyRequest ::= SEQUENCE {
   timeStamp   MinuteOfTheYear             OPTIONAL,
   msgCnt      MsgCount                    OPTIONAL, 
   id          TemporaryID                 OPTIONAL,  
   requests    RequestedItemList,
   
   regional    SEQUENCE (SIZE(1..4)) OF 
               RegionalExtension {{Reg-CommonSafetyRequest}} OPTIONAL,
  ...
}

EmergencyVehicleAlert ::= SEQUENCE {
  timeStamp 		MinuteOfTheYear	    OPTIONAL,
  id 						TemporaryID 				OPTIONAL,
  rsaMsg 				RoadSideAlert,
  responseType	ResponseType				OPTIONAL,
  details 			EmergencyDetails    OPTIONAL,
  mass 					VehicleMass 				OPTIONAL,
  basicType 		VehicleType 				OPTIONAL,
  vehicleType 	VehicleGroupAffected 				OPTIONAL,
  responseEquip IncidentResponseEquipment		OPTIONAL,
  responderType	ResponderGroupAffected 	   	OPTIONAL,
   regional        SEQUENCE (SIZE(1..4)) OF 
                   RegionalExtension {{Reg-EmergencyVehicleAlert}} OPTIONAL,
  ...
}

IntersectionCollision ::= SEQUENCE {
  msgCnt 					MsgCount,
  id 							TemporaryID,
  timeStamp				MinuteOfTheYear	  OPTIONAL,
  partOne 				BSMcoreData 			OPTIONAL,
  path 						PathHistory 			OPTIONAL,
  pathPrediction	PathPrediction   	OPTIONAL,
  intersectionID	IntersectionReferenceID,
  laneNumber 			ApproachOrLane,
  eventFlag 			VehicleEventFlags,
   regional       SEQUENCE (SIZE(1..4)) OF 
                  RegionalExtension {{Reg-IntersectionCollision}} OPTIONAL,
  ...
}

MapData ::= SEQUENCE {
  timeStamp 				MinuteOfTheYear           OPTIONAL, 
  msgIssueRevision 	MsgCount, 
  layerType 				LayerType                 OPTIONAL,
  layerID 					LayerID                   OPTIONAL,
  intersections 		IntersectionGeometryList  OPTIONAL,
  roadSegments 			RoadSegmentList           OPTIONAL,
  dataParameters 		DataParameters            OPTIONAL,
  restrictionList 	RestrictionClassList      OPTIONAL,
   regional          SEQUENCE (SIZE(1..4)) OF 
                     RegionalExtension {{Reg-MapData}} OPTIONAL,
  ...
}

NMEAcorrections ::= SEQUENCE {
  timeStamp 	MinuteOfTheYear	    OPTIONAL,
  rev 		    NMEA-Revision 	    OPTIONAL,
  msg 		    NMEA-MsgType		OPTIONAL,
  wdCount	    ObjectCount 		OPTIONAL,
  payload   	NMEA-Payload,
   regional  SEQUENCE (SIZE(1..4)) OF 
             RegionalExtension {{Reg-NMEAcorrections}} OPTIONAL,
  ...
}


PersonalSafetyMessage ::= SEQUENCE {
  basicType 				PersonalDeviceUserType,
  secMark 					DSecond,
  msgCnt 						MsgCount,
  id 								TemporaryID,
  position 					Position3D, 
  accuracy 					PositionalAccuracy,
  speed 						Velocity,
  heading 					Heading,
  accelSet 					AccelerationSet4Way 					OPTIONAL,
  pathHistory 			PathHistory 									OPTIONAL,
  pathPrediction 		PathPrediction 								OPTIONAL,
  propulsion 				PropelledInformation 					OPTIONAL,
  useState 					PersonalDeviceUsageState 			OPTIONAL,
  crossRequest 			PersonalCrossingRequest 			OPTIONAL,
  crossState 				PersonalCrossingInProgress		OPTIONAL,
  clusterSize 			NumberOfParticipantsInCluster OPTIONAL,
  clusterRadius 		PersonalClusterRadius 				OPTIONAL,
  eventResponderType 	PublicSafetyEventResponderWorkerType 	OPTIONAL,
  activityType 			PublicSafetyAndRoadWorkerActivity 			OPTIONAL,
  activitySubType 	PublicSafetyDirectingTrafficSubType 		OPTIONAL,
  assistType 				PersonalAssistive 						OPTIONAL,
  sizing 						UserSizeAndBehaviour 					OPTIONAL,
  attachment 				Attachment 										OPTIONAL,
  attachmentRadius 	AttachmentRadius 							OPTIONAL,
  animalType 				AnimalType 										OPTIONAL,
  
   regional SEQUENCE (SIZE(1..4)) OF 
            RegionalExtension {{Reg-PersonalSafetyMessage}} OPTIONAL,
  ...
}

ProbeDataManagement ::= SEQUENCE {
  timeStamp           MinuteOfTheYear OPTIONAL, 
  sample              Sample,           
  directions          HeadingSlice,     
  term CHOICE {                          
    termtime          TermTime,         
    termDistance      TermDistance      
   },
  snapshot CHOICE {
    snapshotTime      SnapshotTime,     
    snapshotDistance  SnapshotDistance  
   },
  txInterval          SecondOfTime,     
  dataElements        VehicleStatusRequestList OPTIONAL,
   regional             SEQUENCE (SIZE(1..4)) OF 
                        RegionalExtension {{Reg-ProbeDataManagement}} OPTIONAL,
  ...
}

ProbeVehicleData ::= SEQUENCE {
  timeStamp       MinuteOfTheYear 		OPTIONAL,
  segNum          ProbeSegmentNumber 	OPTIONAL,   
  probeID         VehicleIdent 				OPTIONAL, 
  startVector     FullPositionVector,   
  vehicleType     VehicleClassification,
  snapshots       SEQUENCE (SIZE(1..32)) OF Snapshot,               
   regional        SEQUENCE (SIZE(1..4)) OF 
                   RegionalExtension {{Reg-ProbeVehicleData}} OPTIONAL,
  ...
}

RoadSideAlert ::= SEQUENCE { 
  msgCnt        MsgCount,   
  timeStamp     MinuteOfTheYear  				OPTIONAL,
  typeEvent     ITIScodes,
  description   SEQUENCE (SIZE(1..8)) OF ITIScodes OPTIONAL,
  priority      Priority 								OPTIONAL,  
  heading       HeadingSlice  					OPTIONAL,       
  extent        Extent 									OPTIONAL,  
  position      FullPositionVector 			OPTIONAL, 
  furtherInfoID FurtherInfoID 					OPTIONAL,
   regional      SEQUENCE (SIZE(1..4)) OF 
                 RegionalExtension {{Reg-RoadSideAlert}} OPTIONAL,
  ...
}

RTCMcorrections ::= SEQUENCE {  
  msgCnt      MsgCount,
  rev         RTCM-Revision,
  timeStamp   MinuteOfTheYear  OPTIONAL,  
  anchorPoint FullPositionVector OPTIONAL,
  rtcmHeader  RTCMheader OPTIONAL,   
  msgs        RTCMmessageList,  
  regional    SEQUENCE (SIZE(1..4)) OF 
               RegionalExtension {{Reg-RTCMcorrections}} OPTIONAL,
  ...
  }

SPAT ::= SEQUENCE { 
  timeStamp 			MinuteOfTheYear OPTIONAL, 
  name 						DescriptiveName OPTIONAL, 
  intersections 	IntersectionStateList, 
   regional      SEQUENCE (SIZE(1..4)) OF 
                 RegionalExtension {{Reg-SPAT}} OPTIONAL,
  ...
}

TravelerInformation ::= SEQUENCE {
  msgCnt      MsgCount,  
  timeStamp   MinuteOfTheYear OPTIONAL,
  packetID    UniqueMSGID    OPTIONAL,    
  urlB        URL-Base        OPTIONAL,  
  dataFrames  TravelerDataFrameList,
  
   regional    SEQUENCE (SIZE(1..4)) OF 
               RegionalExtension {{Reg-TravelerInformation}} OPTIONAL,
  ...
}

TrafficLightStatusMessage ::= SEQUENCE { 
  traffiLightID       TrafficLightID-KOR, 
  lon                Longitude            OPTIONAL,
  lat                 Latitude 		         OPTIONAL,
  operationStatus     TrafficLightOperationStatus-KOR,
  controllerStatus    TrafficLightControllerStatus-KOR,
  cycleCounter        TimeInSecond-B16-KOR,
  cycleTime     	    TimeInSecond-B16-KOR, 
  currentTime         DDateTime,
  trafficLightStatus  TrafficLightStatusList-KOR,
  ...
}








AccelerationSet4Way ::= SEQUENCE {
  lon   Acceleration,
  lat    Acceleration,
  vert   VerticalAcceleration,
  yaw    YawRate
}


AccelSteerYawRateConfidence ::= SEQUENCE {
  yawRate             YawRateConfidence, 
  acceleration        AccelerationConfidence, 
  steeringWheelAngle  SteeringWheelAngleConfidence 
}
  
  
AdvisorySpeed ::= SEQUENCE {
  type        AdvisorySpeedType,
  speed       SpeedAdvice 					OPTIONAL,
  confidence  SpeedConfidence 			OPTIONAL,
  distance    ZoneLength 						OPTIONAL,
  class       RestrictionClassID 		OPTIONAL,
   regional    SEQUENCE (SIZE(1..4)) OF 
               RegionalExtension {{Reg-AdvisorySpeed}} OPTIONAL,
  ...
} 


AdvisorySpeedList ::= SEQUENCE (SIZE(1..16)) OF AdvisorySpeed

  
AntennaOffsetSet ::= SEQUENCE {
  antOffsetX   Offset-B12, 
  antOffsetY   Offset-B09, 
  antOffsetZ   Offset-B10 
}


ApproachOrLane ::= CHOICE {
  approach	ApproachID,
  lane			LaneID
}


BrakeSystemStatus ::= SEQUENCE {
  wheelBrakes  BrakeAppliedStatus,
  traction     TractionControlStatus,
  abs          AntiLockBrakeStatus,
  scs          StabilityControlStatus,
  brakeBoost   BrakeBoostApplied,
  auxBrakes    AuxiliaryBrakeStatus
}


BSMcoreData ::= SEQUENCE {
  msgCnt 				MsgCount, 
  id			  		TemporaryID,
  secMark				DSecond,
  lat					Latitude,
  lon					Longitude,
  elev					Elevation,
  accuracy				PositionalAccuracy,	
  transmission			TransmissionState,
  speed					Speed,	
  heading				Heading,
  angle					SteeringWheelAngle,	
  accelSet				AccelerationSet4Way,
  brakes				BrakeSystemStatus,
  size					VehicleSize
}


BumperHeights ::= SEQUENCE {
  front      BumperHeight, 
  rear       BumperHeight
}


Circle ::= SEQUENCE {
  center   Position3D,
  radius   Radius-B12, 
  units    DistanceUnits
}
  

ComputedLane ::= SEQUENCE {
  referenceLaneId   LaneID,
  
  offsetXaxis       CHOICE {
                      small    DrivenLineOffsetSm,
                      large    DrivenLineOffsetLg
                      },
  offsetYaxis       CHOICE {
                      small    DrivenLineOffsetSm,
                      large    DrivenLineOffsetLg
                      },
  
  rotateXY          Angle OPTIONAL,
  
  scaleXaxis        Scale-B12 OPTIONAL,
  scaleYaxis        Scale-B12 OPTIONAL,
  regional          SEQUENCE (SIZE(1..4)) OF 
                    RegionalExtension {{Reg-ComputedLane}} OPTIONAL,
  ...
} 
  
  
ConfidenceSet ::= SEQUENCE {
  accelConfidence      AccelSteerYawRateConfidence 					OPTIONAL,    
  speedConfidence      SpeedandHeadingandThrottleConfidence OPTIONAL,      
  timeConfidence       TimeConfidence 											OPTIONAL,           
  posConfidence        PositionConfidenceSet 								OPTIONAL,           
  steerConfidence      SteeringWheelAngleConfidence 				OPTIONAL,
  headingConfidence    HeadingConfidence 										OPTIONAL,
  throttleConfidence   ThrottleConfidence 									OPTIONAL,
  ...  
}
  
  
ConnectingLane ::= SEQUENCE {
  lane       LaneID,  
  maneuver   AllowedManeuvers OPTIONAL
}                     

                      
Connection ::= SEQUENCE {
  
  connectingLane      ConnectingLane,
  remoteIntersection  IntersectionReferenceID OPTIONAL,
  
  signalGroup         SignalGroupID OPTIONAL,
  userClass           RestrictionClassID OPTIONAL,
  
  connectionID        LaneConnectionID OPTIONAL
} 


ConnectionManeuverAssist ::= SEQUENCE {
  connectionID            LaneConnectionID,
  queueLength             ZoneLength OPTIONAL,
  availableStorageLength  ZoneLength OPTIONAL,
  waitOnStop              WaitOnStopline OPTIONAL,
  pedBicycleDetect        PedestrianBicycleDetect OPTIONAL,
   regional  SEQUENCE (SIZE(1..4)) OF 
             RegionalExtension {{Reg-ConnectionManeuverAssist}} OPTIONAL,
  ...
}


ConnectsToList ::= SEQUENCE (SIZE(1..16)) OF Connection  
  

DataParameters ::= SEQUENCE {
  processMethod    IA5String(SIZE(1..255)) OPTIONAL,
  processAgency    IA5String(SIZE(1..255)) OPTIONAL,
  lastCheckedDate  IA5String(SIZE(1..255)) OPTIONAL,
  geoidUsed        IA5String(SIZE(1..255)) OPTIONAL,
  ...
}  

DDateTime ::= SEQUENCE {
  year   DYear   OPTIONAL,
  month  DMonth  OPTIONAL,
  day    DDay    OPTIONAL,
  hour   DHour   OPTIONAL,
  minute DMinute OPTIONAL,
  second DSecond OPTIONAL,
  offset DOffset OPTIONAL 
}
  













DisabledVehicle ::= SEQUENCE {
  statusDetails     ITIScodes(523..541),   
                    
                    
                    
                    
                    
                    
                    
                    
                    
                    
                    
                    
                    
  locationDetails   GenericLocations   OPTIONAL, 
  ...       
}


EmergencyDetails ::= SEQUENCE {
  notUsed      SSPindex,  
  sirenUse     SirenInUse,                 
  lightsUse    LightbarInUse,              
  multi        MultiVehicleResponse,
  events       PrivilegedEvents OPTIONAL,
  responseType ResponseType OPTIONAL,
  ...
}


EnabledLaneList ::= SEQUENCE (SIZE(1..16)) OF LaneID


EventDescription ::= SEQUENCE {
  typeEvent     ITIScodes,
  description   SEQUENCE (SIZE(1..8)) OF ITIScodes OPTIONAL,  
  priority      Priority OPTIONAL,  
  heading       HeadingSlice  OPTIONAL,       
  extent        Extent OPTIONAL,  
   regional      SEQUENCE (SIZE(1..4)) OF 
                 RegionalExtension {{Reg-EventDescription}} OPTIONAL,
  ...
}
 
  
FullPositionVector ::= SEQUENCE {
  utcTime             DDateTime 						OPTIONAL,  
  lon                Longitude,            
  lat                 Latitude,             
  elevation           Elevation  						OPTIONAL,  
  heading             Heading 							OPTIONAL, 
  speed               TransmissionAndSpeed 	OPTIONAL,
  posAccuracy         PositionalAccuracy 		OPTIONAL,
  timeConfidence      TimeConfidence 				OPTIONAL,
  posConfidence       PositionConfidenceSet OPTIONAL,
  speedConfidence     SpeedandHeadingandThrottleConfidence OPTIONAL, 
  ...
}


GenericLane ::= SEQUENCE {
  laneID           LaneID,
  name             DescriptiveName OPTIONAL,
  ingressApproach  ApproachID OPTIONAL, 
  egressApproach   ApproachID OPTIONAL, 
  laneAttributes   LaneAttributes,
  maneuvers        AllowedManeuvers OPTIONAL,
  nodeList         NodeListXY,
  connectsTo       ConnectsToList OPTIONAL,
  overlays         OverlayLaneList OPTIONAL,
   regional  SEQUENCE (SIZE(1..4)) OF 
             RegionalExtension {{Reg-GenericLane}} OPTIONAL,
  ...
} 


GeographicalPath ::= SEQUENCE {
  name					DescriptiveName					OPTIONAL, 
  id 						RoadSegmentReferenceID	OPTIONAL, 
  anchor				Position3D 							OPTIONAL, 
  laneWidth 		LaneWidth 							OPTIONAL, 
  directionality 	DirectionOfUse 				OPTIONAL, 
  closedPath 		BOOLEAN 								OPTIONAL, 
  direction 		HeadingSlice 						OPTIONAL, 
  description CHOICE {
    path 				OffsetSystem, 
    geometry 		GeometricProjection, 
    oldRegion 	ValidRegion, 
    ...
  } OPTIONAL,

   regional   SEQUENCE (SIZE(1..4)) OF 
            RegionalExtension {{Reg-GeographicalPath}} OPTIONAL,
  ... 
}


GeometricProjection ::= SEQUENCE {
  direction		HeadingSlice,
  extent			Extent	 		OPTIONAL,
  laneWidth 	LaneWidth		OPTIONAL, 
  circle 			Circle,

   regional         SEQUENCE (SIZE(1..4)) OF 
                    RegionalExtension {{Reg-GeometricProjection}} OPTIONAL,
  ...
}






  

  
IntersectionAccessPoint ::= CHOICE {
  lane       LaneID,
  approach   ApproachID,
  connection LaneConnectionID,
  ...
} 
  

IntersectionGeometry ::= SEQUENCE {
  name         DescriptiveName OPTIONAL,
  id           IntersectionReferenceID,
  revision     MsgCount,
  refPoint     Position3D, 
  laneWidth    LaneWidth OPTIONAL,
  speedLimits  SpeedLimitList OPTIONAL,
  laneSet 		 LaneList, 
  preemptPriorityData  PreemptPriorityList OPTIONAL,
   regional     SEQUENCE (SIZE(1..4)) OF 
                RegionalExtension {{Reg-IntersectionGeometry}} OPTIONAL,
  ...
} 

  
IntersectionGeometryList ::= SEQUENCE (SIZE(1..32)) OF IntersectionGeometry  

  
IntersectionReferenceID ::= SEQUENCE {
  region  RoadRegulatorID OPTIONAL,
  id      IntersectionID
}


IntersectionState ::= SEQUENCE {
  name          DescriptiveName OPTIONAL,
  id            IntersectionReferenceID,
  revision      MsgCount,
  status        IntersectionStatusObject,
  moy           MinuteOfTheYear OPTIONAL,
  timeStamp     DSecond OPTIONAL,
  enabledLanes  EnabledLaneList OPTIONAL,
  states        MovementList,
  maneuverAssistList  ManeuverAssistList OPTIONAL,

   regional     SEQUENCE (SIZE(1..4)) OF 
                RegionalExtension {{Reg-IntersectionState}} OPTIONAL,
  ...
}


IntersectionStateList ::= SEQUENCE (SIZE(1..32)) OF IntersectionState


ExitService ::= SEQUENCE (SIZE(1..16)) OF SEQUENCE {
  item CHOICE {
    itis ITIScodes,
    text ITIStextPhrase
    }
}
  
  
GenericSignage ::= SEQUENCE (SIZE(1..16)) OF SEQUENCE {
  item CHOICE {
    itis ITIScodes,
    text ITIStextPhrase
    }
}
  

SpeedLimit ::= SEQUENCE (SIZE(1..16)) OF SEQUENCE {
  item CHOICE {
    itis ITIScodes,
    text ITIStextPhrase
  }
}
  

WorkZone ::= SEQUENCE (SIZE(1..16)) OF SEQUENCE {
  item CHOICE {
    itis ITIScodes,
    text ITIStextPhrase
  }
}

  
J1939data ::= SEQUENCE {
  tires                    TireDataList              OPTIONAL,
  axles                    AxleWeightList            OPTIONAL,      
  trailerWeight            TrailerWeight             OPTIONAL,     
  cargoWeight              CargoWeight               OPTIONAL, 
  steeringAxleTemperature  SteeringAxleTemperature   OPTIONAL, 
  driveAxleLocation        DriveAxleLocation         OPTIONAL, 
  driveAxleLiftAirPressure DriveAxleLiftAirPressure  OPTIONAL, 
  driveAxleTemperature     DriveAxleTemperature      OPTIONAL, 
  driveAxleLubePressure    DriveAxleLubePressure     OPTIONAL, 
  steeringAxleLubePressure SteeringAxleLubePressure  OPTIONAL, 
  ...
}  


TireDataList ::= SEQUENCE (SIZE(1..16)) OF TireData


TireData ::= SEQUENCE {
  location              TireLocation              OPTIONAL, 
  pressure              TirePressure              OPTIONAL, 
  temp                  TireTemp                  OPTIONAL, 
  wheelSensorStatus     WheelSensorStatus         OPTIONAL, 
  wheelEndElectFault    WheelEndElectFault        OPTIONAL, 
  leakageRate           TireLeakageRate           OPTIONAL, 
  detection             TirePressureThresholdDetection OPTIONAL, 
  ...
}
  
AxleWeightList ::= SEQUENCE (SIZE(1..16)) OF AxleWeightSet

AxleWeightSet ::= SEQUENCE {
  location AxleLocation OPTIONAL,
  weight 	 AxleWeight 	OPTIONAL,
  ...
}


LaneAttributes ::= SEQUENCE {
  directionalUse  LaneDirection,      
  sharedWith      LaneSharing,        
  laneType        LaneTypeAttributes, 
   regional        RegionalExtension {{Reg-LaneAttributes}} OPTIONAL
}


LaneDataAttribute ::= CHOICE {
  pathEndPointAngle        DeltaAngle,
  laneCrownPointCenter     RoadwayCrownAngle,
  laneCrownPointLeft       RoadwayCrownAngle,
  laneCrownPointRight      RoadwayCrownAngle,
  laneAngle                MergeDivergeNodeAngle,
  speedLimits              SpeedLimitList,
    regional  SEQUENCE (SIZE(1..4)) OF 
              RegionalExtension {{Reg-LaneDataAttribute}},
  ...
}


LaneDataAttributeList ::= SEQUENCE (SIZE(1..8)) OF LaneDataAttribute


LaneList ::= SEQUENCE (SIZE(1..255)) OF GenericLane


LaneTypeAttributes ::= CHOICE {
  vehicle         LaneAttributes-Vehicle,         
  crosswalk       LaneAttributes-Crosswalk,       
  bikeLane        LaneAttributes-Bike,            
  sidewalk        LaneAttributes-Sidewalk,        
  median          LaneAttributes-Barrier,         
  striping        LaneAttributes-Striping,        
  trackedVehicle  LaneAttributes-TrackedVehicle,  
  parking         LaneAttributes-Parking,         
  ...
}


ManeuverAssistList ::= SEQUENCE (SIZE(1..16)) OF ConnectionManeuverAssist


MovementEventList ::= SEQUENCE (SIZE(1..16)) OF MovementEvent


MovementEvent ::= SEQUENCE {
  eventState   MovementPhaseState,
  timing       TimeChangeDetails OPTIONAL,
  speeds       AdvisorySpeedList OPTIONAL,
   regional     SEQUENCE (SIZE(1..4)) OF 
                RegionalExtension {{Reg-MovementEvent}} OPTIONAL,
  ...
}


MovementList ::= SEQUENCE (SIZE(1..255)) OF MovementState


MovementState ::= SEQUENCE {
  movementName        DescriptiveName OPTIONAL,
  signalGroup         SignalGroupID,
  state-time-speed    MovementEventList,
  maneuverAssistList  ManeuverAssistList OPTIONAL,
   regional           SEQUENCE (SIZE(1..4)) OF 
                      RegionalExtension {{Reg-MovementState}} OPTIONAL,
  ...
}


Node-LL-24B ::= SEQUENCE {
  lon  OffsetLL-B12,
  lat  OffsetLL-B12
}


Node-LL-28B ::= SEQUENCE {
  lon  OffsetLL-B14,
  lat  OffsetLL-B14
}


Node-LL-32B ::= SEQUENCE {
  lon  OffsetLL-B16,
  lat  OffsetLL-B16
}


Node-LL-36B ::= SEQUENCE {
  lon  OffsetLL-B18,
  lat  OffsetLL-B18
}


Node-LL-44B ::= SEQUENCE {
  lon  OffsetLL-B22,
  lat  OffsetLL-B22
}


Node-LL-48B ::= SEQUENCE {
  lon  OffsetLL-B24,
  lat  OffsetLL-B24
}
  

Node-LLmD-64b ::= SEQUENCE {
  lon  Longitude,
  lat  Latitude
}


Node-XY-20b ::= SEQUENCE {
  x  Offset-B10,
  y  Offset-B10
}


Node-XY-22b ::= SEQUENCE {
  x  Offset-B11,
  y  Offset-B11
}


Node-XY-24b ::= SEQUENCE {
  x  Offset-B12,
  y  Offset-B12
}


Node-XY-26b ::= SEQUENCE {
  x  Offset-B13,
  y  Offset-B13
}


Node-XY-28b ::= SEQUENCE {
  x  Offset-B14,
  y  Offset-B14
}


Node-XY-32b ::= SEQUENCE {
  x  Offset-B16,
  y  Offset-B16
}


NodeAttributeLLList ::= SEQUENCE (SIZE(1..8)) OF NodeAttributeLL


NodeAttributeSetLL ::= SEQUENCE {
  localNode 	NodeAttributeLLList 		OPTIONAL,
  disabled 		SegmentAttributeLLList	OPTIONAL,
  enabled 		SegmentAttributeLLList	OPTIONAL,
  data 				LaneDataAttributeList 	OPTIONAL,
  dWidth 			Offset-B10 							OPTIONAL,
  dElevation 	Offset-B10 							OPTIONAL,
   regional     SEQUENCE (SIZE(1..4)) OF 
                RegionalExtension {{Reg-NodeAttributeSetLL}} OPTIONAL,
  ...
}
  

NodeAttributeSetXY ::= SEQUENCE {
  localNode   NodeAttributeXYList OPTIONAL,
  disabled    SegmentAttributeXYList OPTIONAL,
  enabled     SegmentAttributeXYList OPTIONAL,
  data        LaneDataAttributeList OPTIONAL,
  dWidth      Offset-B10 OPTIONAL,
  dElevation  Offset-B10 OPTIONAL,
   regional     SEQUENCE (SIZE(1..4)) OF 
                RegionalExtension {{Reg-NodeAttributeSetXY}} OPTIONAL,
   ...
}


NodeAttributeXYList ::= SEQUENCE (SIZE(1..8)) OF NodeAttributeXY


NodeListLL ::= CHOICE {
  nodes  NodeSetLL,
  ...
}


NodeListXY ::= CHOICE {
  nodes     NodeSetXY,
  computed  ComputedLane,
  ...
}


NodeLL ::= SEQUENCE {
  delta       NodeOffsetPointLL,
  attributes  NodeAttributeSetLL OPTIONAL,
  ...
}
  

NodeOffsetPointLL ::= CHOICE {
  node-LL1     Node-LL-24B,    
  node-LL2     Node-LL-28B,    
  node-LL3     Node-LL-32B,    
  node-LL4     Node-LL-36B,   
  node-LL5     Node-LL-44B,    
  node-LL6     Node-LL-48B,    
  node-LatLon  Node-LLmD-64b,  
   regional         RegionalExtension {{Reg-NodeOffsetPointLL}}
}
  
  
NodeOffsetPointXY ::= CHOICE {
  node-XY1     Node-XY-20b,   
  node-XY2     Node-XY-22b,   
  node-XY3     Node-XY-24b,   
  node-XY4     Node-XY-26b,   
  node-XY5     Node-XY-28b,   
  node-XY6     Node-XY-32b,   
  node-LatLon  Node-LLmD-64b, 
   regional         RegionalExtension {{Reg-NodeOffsetPointXY}}
}


NodeSetLL ::= SEQUENCE (SIZE(2..63)) OF NodeLL

NodeSetXY ::= SEQUENCE (SIZE(2..63)) OF NodeXY

NodeXY ::= SEQUENCE {
  delta       NodeOffsetPointXY,
  attributes  NodeAttributeSetXY OPTIONAL,
  ...
}

ObstacleDetection ::= SEQUENCE {  
  obDist          ObstacleDistance,      
  obDirect        ObstacleDirection,     
  description     ITIScodes(523..541) OPTIONAL, 
  locationDetails GenericLocations OPTIONAL,        
  dateTime        DDateTime,             
  vertEvent       VerticalAccelerationThreshold OPTIONAL, 
  ...
}


OffsetSystem ::= SEQUENCE { 
  scale    Zoom OPTIONAL, 
  offset   CHOICE {
    xy 	    NodeListXY, 
    ll 	    NodeListLL 
    } 
}
  

OverlayLaneList ::= SEQUENCE (SIZE(1..5)) OF LaneID


PathHistory ::= SEQUENCE {
  initialPosition  FullPositionVector    OPTIONAL,
  currGNSSstatus   GNSSstatus            OPTIONAL,   
  crumbData  	   PathHistoryPointList,
  ...
}


PathHistoryPointList ::= SEQUENCE (SIZE (1..23)) OF PathHistoryPoint


PathHistoryPoint ::= SEQUENCE {
  latOffset       OffsetLL-B18,
  lonOffset       OffsetLL-B18,
  elevationOffset VertOffset-B12,  
  timeOffset      TimeOffset,
  speed           Speed                 OPTIONAL, 
  posAccuracy     PositionalAccuracy    OPTIONAL, 
  heading         CoarseHeading         OPTIONAL,
   ...
}


PathPrediction ::= SEQUENCE {
  radiusOfCurve RadiusOfCurvature, 
  confidence    Confidence, 
  ...
}


PivotPointDescription ::= SEQUENCE {
  pivotOffset  Offset-B11,   
  pivotAngle   Angle,
  pivots       PivotingAllowed,
  ...
}


Position3D ::= SEQUENCE {
  lat        Latitude,                
  lon       Longitude,               
  elevation  Elevation OPTIONAL,      
   regional   SEQUENCE (SIZE(1..4)) OF 
              RegionalExtension {{Reg-Position3D}} OPTIONAL,
  ...
}


PositionalAccuracy ::= SEQUENCE {
  semiMajor     SemiMajorAxisAccuracy,
  semiMinor     SemiMinorAxisAccuracy,
  orientation   SemiMajorAxisOrientation
}


PositionConfidenceSet ::= SEQUENCE {
  pos        PositionConfidence, 
  elevation  ElevationConfidence 
}


PreemptPriorityList ::= SEQUENCE (SIZE(1..32)) OF SignalControlZone

SignalControlZone ::= SEQUENCE {
  zone  RegionalExtension {{Reg-SignalControlZone}},
  ...
}


PrivilegedEvents ::= SEQUENCE {
  notUsed   SSPindex,  
  event     PrivilegedEventFlags,
  ...
}


PropelledInformation ::= CHOICE {
  human   HumanPropelledType, 
  animal  AnimalPropelledType,
  motor   MotorizedPropelledType,
  ...
}
  

RegionList ::= SEQUENCE (SIZE(1..64)) OF RegionOffsets  


RegionOffsets ::= SEQUENCE {
  xOffset 	OffsetLL-B16,
  yOffset 	OffsetLL-B16,
  zOffset 	OffsetLL-B16 OPTIONAL
}
  

RegionPointSet ::= SEQUENCE {
  anchor 	Position3D	OPTIONAL,
  scale 	Zoom		OPTIONAL,
  nodeList 	RegionList,
  ...
}


RegulatorySpeedLimit ::= SEQUENCE {
  type 	SpeedLimitType, 
  speed	Velocity
}
  

RequestedItemList ::= SEQUENCE (SIZE(1..32)) OF RequestedItem


RequestorDescription ::= SEQUENCE {
  id                VehicleID,
  type              RequestorType OPTIONAL,
  position          RequestorPositionVector OPTIONAL,
  name              DescriptiveName OPTIONAL,
  routeName         DescriptiveName OPTIONAL,
  transitStatus     TransitVehicleStatus OPTIONAL,
  transitOccupancy  TransitVehicleOccupancy OPTIONAL,
  transitSchedule   DeltaTime OPTIONAL,

   regional          SEQUENCE (SIZE(1..4)) OF 
                     RegionalExtension {{Reg-RequestorDescription}} OPTIONAL,
  ...
}


RequestorPositionVector ::= SEQUENCE {
  position            Position3D,
  heading             Angle OPTIONAL,
  speed               TransmissionAndSpeed OPTIONAL,
  ...
}


RequestorType ::= SEQUENCE {
  role        BasicVehicleRole,  
  subrole     RequestSubRole  OPTIONAL,  
  request     RequestImportanceLevel  OPTIONAL,  
  iso3883     Iso3833VehicleType  OPTIONAL,
  hpmsType    VehicleType OPTIONAL,  
   regional     RegionalExtension {{Reg-RequestorType}} OPTIONAL,
  ...
}


RestrictionClassAssignment ::= SEQUENCE {
  id        RestrictionClassID,
  users     RestrictionUserTypeList
}


RestrictionClassList ::= SEQUENCE (SIZE(1..254)) OF RestrictionClassAssignment


RestrictionUserTypeList ::= SEQUENCE (SIZE(1..16)) OF RestrictionUserType


RestrictionUserType ::= CHOICE {
  basicType    RestrictionAppliesTo,
   regional    SEQUENCE (SIZE(1..4)) OF 
               RegionalExtension {{Reg-RestrictionUserType}}, 
  ...
}


RoadLaneSetList ::= SEQUENCE (SIZE(1..255)) OF GenericLane


RoadSegmentList ::= SEQUENCE (SIZE(1..32)) OF RoadSegment


RoadSegmentReferenceID ::= SEQUENCE {
  region  RoadRegulatorID OPTIONAL,
  id      RoadSegmentID
}


RoadSegment ::= SEQUENCE {
  name         DescriptiveName OPTIONAL,
  id           RoadSegmentReferenceID,
  revision     MsgCount,
  refPoint     Position3D,  
  laneWidth    LaneWidth OPTIONAL,
  speedLimits  SpeedLimitList OPTIONAL,
  roadLaneSet  RoadLaneSetList,
   regional    SEQUENCE (SIZE(1..4)) OF 
               RegionalExtension {{Reg-RoadSegment}} OPTIONAL,
  ...
}


RoadSignID ::= SEQUENCE {
  position  Position3D,  
  viewAngle	HeadingSlice, 
  mutcdCode	MUTCDCode 	OPTIONAL,
  crc 			MsgCRC 			OPTIONAL 
}

  
RTCMheader ::= SEQUENCE {
  status     GNSSstatus,
  offsetSet  AntennaOffsetSet
}


RTCMmessageList ::= SEQUENCE (SIZE(1..5)) OF RTCMmessage


RTCMPackage ::= SEQUENCE {  
  rtcmHeader  RTCMheader OPTIONAL,  
  msgs        RTCMmessageList,
  ...  
}


Sample ::= SEQUENCE {
  sampleStart  INTEGER(0..255),  
  sampleEnd    INTEGER(0..255)   
}
  

SegmentAttributeLLList ::= SEQUENCE (SIZE(1..8)) OF SegmentAttributeLL  


SegmentAttributeXYList ::= SEQUENCE (SIZE(1..8)) OF SegmentAttributeXY


ShapePointSet ::= SEQUENCE {
  anchor 					Position3D	  	OPTIONAL,
  laneWidth				LaneWidth				OPTIONAL,
  directionality	DirectionOfUse	OPTIONAL,
  nodeList 				NodeListXY, 
  ...
}
  
  
SignalRequesterInfo ::= SEQUENCE {
  id              VehicleID,
  request         RequestID,
  sequenceNumber  MsgCount,
  role            BasicVehicleRole OPTIONAL,
  typeData        RequestorType OPTIONAL,
  ...
}


SignalRequestList ::= SEQUENCE (SIZE(1..32)) OF SignalRequestPackage


SignalRequestPackage ::= SEQUENCE {
  request    SignalRequest,
  minute     MinuteOfTheYear OPTIONAL,
  second     DSecond OPTIONAL,
  duration   DSecond OPTIONAL,
   regional       SEQUENCE (SIZE(1..4)) OF 
                  RegionalExtension {{Reg-SignalRequestPackage}} OPTIONAL,
  ...
}

SignalRequest ::= SEQUENCE {
  id            IntersectionReferenceID,
  requestID     RequestID,
  requestType   PriorityRequestType,
  inBoundLane   IntersectionAccessPoint,
  outBoundLane  IntersectionAccessPoint OPTIONAL,
   regional      SEQUENCE (SIZE(1..4)) OF 
                 RegionalExtension {{Reg-SignalRequest}} OPTIONAL,
  ...
}


SignalStatusList ::= SEQUENCE (SIZE(1..32)) OF SignalStatus

SignalStatusPackageList ::= SEQUENCE (SIZE(1..32)) OF SignalStatusPackage

SignalStatusPackage ::= SEQUENCE {
  requester    SignalRequesterInfo  OPTIONAL,
  inboundOn    IntersectionAccessPoint,  
  outboundOn   IntersectionAccessPoint  OPTIONAL,
  minute       MinuteOfTheYear  OPTIONAL,
  second       DSecond  OPTIONAL,
  duration     DSecond  OPTIONAL,
  status       PrioritizationResponseStatus,
   regional     SEQUENCE (SIZE(1..4)) OF 
                RegionalExtension {{Reg-SignalStatusPackage}} OPTIONAL,
  ...
}


SignalStatus ::= SEQUENCE {
  sequenceNumber  MsgCount,
  id              IntersectionReferenceID,
  sigStatus       SignalStatusPackageList,
   regional       SEQUENCE (SIZE(1..4)) OF 
                  RegionalExtension {{Reg-SignalStatus}} OPTIONAL,
  ...
}


SnapshotDistance ::= SEQUENCE {
  distance1   GrossDistance,  
  speed1      GrossSpeed,     
  distance2   GrossDistance,  
  speed2      GrossSpeed      
}


Snapshot ::= SEQUENCE {
  thePosition  FullPositionVector,          
  safetyExt    VehicleSafetyExtensions OPTIONAL, 
  dataSet      VehicleStatus           OPTIONAL,  
  ...  
}
  

SnapshotTime ::= SEQUENCE {
  speed1  GrossSpeed,     
  time1   SecondOfTime,   
  speed2  GrossSpeed,     
  time2   SecondOfTime    
}

  
SpecialVehicleExtensions ::= SEQUENCE {
  vehicleAlerts  EmergencyDetails OPTIONAL,
  description    EventDescription  OPTIONAL, 
  trailers       TrailerData OPTIONAL,
  ...
}


SpeedandHeadingandThrottleConfidence ::= SEQUENCE {
  heading   HeadingConfidence,    
  speed     SpeedConfidence,      
  throttle  ThrottleConfidence    
}


SpeedLimitList ::= SEQUENCE (SIZE(1..9)) OF RegulatorySpeedLimit


SpeedProfileMeasurementList ::= SEQUENCE (SIZE(1..20)) OF SpeedProfileMeasurement

SpeedProfile ::= SEQUENCE {
  speedReports SpeedProfileMeasurementList,  
  ...
}


SupplementalVehicleExtensions ::= SEQUENCE {
  classification   BasicVehicleClass        OPTIONAL,
  classDetails     VehicleClassification    OPTIONAL,
  vehicleData      VehicleData              OPTIONAL,
  weatherReport    WeatherReport            OPTIONAL, 
  weatherProbe     WeatherProbe             OPTIONAL, 
  obstacle         ObstacleDetection        OPTIONAL,
  status           DisabledVehicle          OPTIONAL,
  speedProfile     SpeedProfile             OPTIONAL, 
  theRTCM          RTCMPackage              OPTIONAL, 

   regional  SEQUENCE (SIZE(1..4)) OF 
             RegionalExtension {{Reg-SupplementalVehicleExtensions}} OPTIONAL,
  ...   
}


TimeChangeDetails ::= SEQUENCE {
  startTime   TimeMark                OPTIONAL,
  minEndTime  TimeMark,
  maxEndTime  TimeMark                OPTIONAL,
  likelyTime  TimeMark                OPTIONAL,
  confidence  TimeIntervalConfidence  OPTIONAL,
  nextTime    TimeMark                OPTIONAL
}


TrailerData ::= SEQUENCE {
  notUsed   SSPindex,  
  connection  PivotPointDescription, 
  units       TrailerUnitDescriptionList,
  ...
}

TrailerHistoryPointList ::= SEQUENCE (SIZE(1..23)) OF TrailerHistoryPoint

TrailerHistoryPoint ::= SEQUENCE {
  pivotAngle		Angle,
  timeOffset		TimeOffset,
  positionOffset	Node-XY-24b, 
  elevationOffset   VertOffset-B07		OPTIONAL,
  heading			CoarseHeading		OPTIONAL,
  ...
}


TrailerUnitDescriptionList ::= SEQUENCE (SIZE(1..8)) OF TrailerUnitDescription


TrailerUnitDescription ::= SEQUENCE {
  isDolly          IsDolly, 
  width            VehicleWidth,   
  length           VehicleLength,  
  height           VehicleHeight OPTIONAL,
  mass             TrailerMass   OPTIONAL,
  bumperHeights    BumperHeights OPTIONAL,
  centerOfGravity  VehicleHeight OPTIONAL,
  frontPivot       PivotPointDescription,
  rearPivot        PivotPointDescription OPTIONAL,
  rearWheelOffset  Offset-B12 OPTIONAL,   
  positionOffset   Node-XY-24b, 
  elevationOffset  VertOffset-B07 OPTIONAL,   
  crumbData  	    TrailerHistoryPointList OPTIONAL, 
  ...
}


TransmissionAndSpeed ::= SEQUENCE {
  transmission	TransmissionState,
  speed					Velocity
}


TravelerDataFrameList ::= SEQUENCE (SIZE(1..8)) OF TravelerDataFrame

TravelerDataFrame ::= SEQUENCE {
  notUsed   	SSPindex,
  frameType 	TravelerInfoType,
  msgId CHOICE {
    furtherInfoID 	FurtherInfoID,
    roadSignID 			RoadSignID
    },
  startYear	    DYear                  OPTIONAL,
  startTime	    MinuteOfTheYear,
  durationTime  MinutesDuration,
  priority	    SignPrority,
  
  notUsed1	    SSPindex,
  regions       SEQUENCE (SIZE(1..16)) OF GeographicalPath,

  notUsed2	    SSPindex,
  notUsed3 	    SSPindex,
  content CHOICE {
    advisory			ITIScodesAndText,
    workZone 			WorkZone,
    genericSign 	GenericSignage,
    speedLimit 	   SpeedLimit,
    exitService 	ExitService
  },
  url           URL-Short OPTIONAL,
  ...
}


ValidRegion ::= SEQUENCE {
  direction    	HeadingSlice,
  extent 		Extent OPTIONAL,
  area CHOICE {
    shapePointSet 	ShapePointSet,
    circle 			Circle,
    regionPointSet	RegionPointSet
  }
}
  

VehicleClassification ::= SEQUENCE {
  keyType         BasicVehicleClass OPTIONAL,

  role            BasicVehicleRole OPTIONAL, 
  iso3883         Iso3833VehicleType OPTIONAL,
  hpmsType        VehicleType OPTIONAL,  

  vehicleType     VehicleGroupAffected OPTIONAL,      
  responseEquip   IncidentResponseEquipment OPTIONAL, 
  responderType   ResponderGroupAffected OPTIONAL,    
  fuelType        FuelType OPTIONAL,      

   regional        SEQUENCE (SIZE(1..4)) OF 
                   RegionalExtension {{Reg-VehicleClassification}} OPTIONAL,
  ...
}


VehicleData ::= SEQUENCE {    
  height        VehicleHeight   OPTIONAL,
  bumpers       BumperHeights   OPTIONAL,
  mass          VehicleMass     OPTIONAL,
  trailerWeight TrailerWeight   OPTIONAL,
  ...
}


VehicleIdent ::= SEQUENCE {
  name 					DescriptiveName 		OPTIONAL,
  vin 					VINstring 					OPTIONAL,
  ownerCode 		IA5String(SIZE(1..32))      OPTIONAL,
  id 						VehicleID 					OPTIONAL, 
  vehicleType 	VehicleType 				OPTIONAL, 
  vehicleClass  CHOICE {
    vGroup 	VehicleGroupAffected, 
    rGroup 	ResponderGroupAffected, 
    rEquip 	IncidentResponseEquipment 
    } OPTIONAL, 
  ... 
}
  
  
VehicleID ::= CHOICE {
  entityID     TemporaryID,
  stationID    StationID
}


VehicleSafetyExtensions ::= SEQUENCE {
  events          VehicleEventFlags OPTIONAL,
  pathHistory     PathHistory OPTIONAL,
  pathPrediction  PathPrediction OPTIONAL,
  lights          ExteriorLights OPTIONAL,
  ...
}


VehicleSize ::= SEQUENCE {
  width   VehicleWidth,
  length  VehicleLength
}


VehicleStatusRequest ::= SEQUENCE {
  dataType             VehicleStatusDeviceTypeTag, 
  subType              INTEGER (1..15)   OPTIONAL, 
  sendOnLessThenValue  INTEGER (-32767..32767) OPTIONAL, 
  sendOnMoreThenValue  INTEGER (-32767..32767) OPTIONAL, 
  sendAll              BOOLEAN OPTIONAL, 
  ... 
  }


VehicleStatusRequestList ::= SEQUENCE (SIZE(1..32)) OF VehicleStatusRequest


VehicleStatus ::= SEQUENCE { 
  lights          ExteriorLights OPTIONAL,         
  lightBar        LightbarInUse  OPTIONAL,         

  wipers          WiperSet OPTIONAL,               

  brakeStatus     BrakeSystemStatus OPTIONAL, 
  brakePressure   BrakeAppliedPressure  OPTIONAL,   
  roadFriction    CoefficientOfFriction OPTIONAL,   

  sunData         SunSensor             OPTIONAL,   
  rainData        RainSensor            OPTIONAL,   
  airTemp         AmbientAirTemperature OPTIONAL,   
  airPres         AmbientAirPressure    OPTIONAL,   

  steering   SEQUENCE {
    angle          SteeringWheelAngle,   
    confidence     SteeringWheelAngleConfidence   OPTIONAL,    
    rate           SteeringWheelAngleRateOfChange OPTIONAL,   
    wheels         DrivingWheelAngle              OPTIONAL
  } OPTIONAL,                       

  accelSets  SEQUENCE {
    accel4way       AccelerationSet4Way           OPTIONAL, 
    vertAccelThres  VerticalAccelerationThreshold OPTIONAL, 
    yawRateCon      YawRateConfidence             OPTIONAL, 
    hozAccelCon     AccelerationConfidence        OPTIONAL,     
    confidenceSet   ConfidenceSet                 OPTIONAL
  } OPTIONAL, 

  object     SEQUENCE {
    obDist          ObstacleDistance,   
    obDirect        Angle,              
    dateTime        DDateTime           
  } OPTIONAL,                           

  fullPos         FullPositionVector OPTIONAL,  
  throttlePos     ThrottlePosition OPTIONAL,
  speedHeadC      SpeedandHeadingandThrottleConfidence OPTIONAL,    
  speedC          SpeedConfidence OPTIONAL,

  vehicleData   SEQUENCE {    
    height        VehicleHeight,
    bumpers       BumperHeights,
    mass          VehicleMass,
    trailerWeight TrailerWeight,
    type          VehicleType 
  } OPTIONAL,                         

  vehicleIdent   VehicleIdent OPTIONAL,  

  j1939data      J1939data OPTIONAL,     
  weatherReport SEQUENCE {    
    isRaining        EssPrecipYesNo,
    rainRate         EssPrecipRate       OPTIONAL,
    precipSituation  EssPrecipSituation  OPTIONAL,
    solarRadiation   EssSolarRadiation   OPTIONAL,
    friction         EssMobileFriction   OPTIONAL
  } OPTIONAL,                                        

  gnssStatus      GNSSstatus          OPTIONAL,              
 
   ...          
   }
  
WeatherProbe ::= SEQUENCE {
  airTemp      AmbientAirTemperature OPTIONAL,
  airPressure  AmbientAirPressure OPTIONAL,
  rainRates    WiperSet OPTIONAL,
  ...
}


WeatherReport ::= SEQUENCE {    
  isRaining        EssPrecipYesNo,
  rainRate         EssPrecipRate       OPTIONAL,
  precipSituation  EssPrecipSituation  OPTIONAL,
  solarRadiation   EssSolarRadiation   OPTIONAL,
  friction         EssMobileFriction   OPTIONAL,
  roadFriction     CoefficientOfFriction     OPTIONAL,   
  ... 
}


WiperSet ::= SEQUENCE {
  statusFront  WiperStatus,
  rateFront    WiperRate,
  statusRear   WiperStatus OPTIONAL,
  rateRear     WiperRate OPTIONAL
}

 




  

























Reg-AdvisorySpeed 		REG-EXT-ID-AND-TYPE ::= { ... }
Reg-ComputedLane 		REG-EXT-ID-AND-TYPE ::= { ... }
Reg-EventDescription 	REG-EXT-ID-AND-TYPE ::= { 
  { EventDescription-KOR IDENTIFIED BY addGrpD} , 
     ... 
}
Reg-GenericLane REG-EXT-ID-AND-TYPE ::= { ... }
Reg-GeographicalPath      REG-EXT-ID-AND-TYPE ::= { 
    { GeographicalPath-KOR IDENTIFIED BY addGrpD} ,
    ...  
}
Reg-GeometricProjection 	REG-EXT-ID-AND-TYPE ::= { ... }
Reg-IntersectionGeometry 	REG-EXT-ID-AND-TYPE ::= { ... }
Reg-LaneAttributes 			REG-EXT-ID-AND-TYPE ::= { ... }
Reg-MovementState 			REG-EXT-ID-AND-TYPE ::= { ... }
Reg-NodeAttributeSetLL 		REG-EXT-ID-AND-TYPE ::= { ... }
Reg-NodeAttributeSetXY 		REG-EXT-ID-AND-TYPE ::= { ... }
Reg-NodeOffsetPointLL 		REG-EXT-ID-AND-TYPE ::= { ... }
Reg-RequestorDescription 	REG-EXT-ID-AND-TYPE ::= { ... }
Reg-RequestorType 			REG-EXT-ID-AND-TYPE ::= { ... }
Reg-RoadSegment 			REG-EXT-ID-AND-TYPE ::= { ... }
Reg-SignalControlZone 		REG-EXT-ID-AND-TYPE ::= { ... }
Reg-SignalRequest 			REG-EXT-ID-AND-TYPE ::= { ... }
Reg-SignalRequestPackage 	REG-EXT-ID-AND-TYPE ::= { ... }
Reg-SignalStatus 			REG-EXT-ID-AND-TYPE ::= { ... }
Reg-SignalStatusPackage 	REG-EXT-ID-AND-TYPE ::= { ... }
Reg-SupplementalVehicleExtensions REG-EXT-ID-AND-TYPE ::= { 
  { SupplementalVehicleExtensions-KOR IDENTIFIED BY addGrpD} , 
  ... 
}
Reg-VehicleClassification 	REG-EXT-ID-AND-TYPE ::= { 
  { VehicleClassification-KOR IDENTIFIED BY addGrpD} , 
  ... 
}


Reg-ConnectionManeuverAssist REG-EXT-ID-AND-TYPE ::= { 
	... 
}
Reg-IntersectionState 		REG-EXT-ID-AND-TYPE ::= { 
	... 
}
Reg-LaneDataAttribute 		REG-EXT-ID-AND-TYPE ::= { 
	... 
}
Reg-MovementEvent 			REG-EXT-ID-AND-TYPE ::= { 
	... 
}
Reg-NodeOffsetPointXY 		REG-EXT-ID-AND-TYPE ::= { 
	... 
}
Reg-Position3D 				REG-EXT-ID-AND-TYPE ::= { 
	... 
}
Reg-RestrictionUserType 	REG-EXT-ID-AND-TYPE ::= { 
	... 
}
Reg-BasicSafetyMessage 		REG-EXT-ID-AND-TYPE ::= { 
  { BasicSafetyMessage-KOR IDENTIFIED BY addGrpD},
  ... 
}

Reg-CommonSafetyRequest 	REG-EXT-ID-AND-TYPE ::= { ... }

Reg-EmergencyVehicleAlert 	REG-EXT-ID-AND-TYPE ::= { 
	{ EmergencyVehicleAlert-KOR IDENTIFIED BY addGrpD},
	... 
}

Reg-IntersectionCollision  REG-EXT-ID-AND-TYPE ::= { 
	{ IntersectionCollisionAvoidance-KOR IDENTIFIED BY addGrpD},
	... 
}
Reg-NMEAcorrections 		REG-EXT-ID-AND-TYPE ::= { ... }
Reg-ProbeDataManagement 	REG-EXT-ID-AND-TYPE ::= { ... }
Reg-ProbeVehicleData 		REG-EXT-ID-AND-TYPE ::= { 
    { ProbeVehicleData-KOR IDENTIFIED BY addGrpD},
    ... 
}
Reg-RoadSideAlert          REG-EXT-ID-AND-TYPE ::= { 
    { RoadSideAlert-KOR IDENTIFIED BY addGrpD},
    ... 
}
Reg-RTCMcorrections 		REG-EXT-ID-AND-TYPE ::= { ... }
Reg-SPAT 					REG-EXT-ID-AND-TYPE ::= { ... }
Reg-TravelerInformation    REG-EXT-ID-AND-TYPE ::= { 
    { TravelerInformation-KOR IDENTIFIED BY addGrpD},
    ... 
}
Reg-PersonalSafetyMessage  REG-EXT-ID-AND-TYPE ::= {
    { PersonalSafetyMessage-KOR  IDENTIFIED BY addGrpD},
    ... 
}
Reg-MapData REG-EXT-ID-AND-TYPE ::= { 
	... 
}

BasicSafetyMessage-KOR ::= SEQUENCE {
  adas                  SEQUENCE(SIZE(0..12)) OF CITSADAS-KOR           OPTIONAL,
  typeEvent		        ITIScodes 	           OPTIONAL,
  laneID			    LaneID 			       OPTIONAL,
  roadSegmentRef        RoadSegmentReferenceID OPTIONAL,
  dectLane		        DectLane-KOR		   OPTIONAL,
  verticalHeading	    VerticalHeading-KOR	   OPTIONAL,
  brakePedalCmd         BrakePedalCmd-KOR      OPTIONAL,
  brakePedalPressure    BrakePedalPressure-KOR OPTIONAL,
  eventFlags		    VehicleEventFlags-KOR  OPTIONAL,
  wheelAngle		    WheelAngles-KOR        OPTIONAL,
  responseType          ResponseType-KOR       OPTIONAL,
  ...
}

CITSADAS-KOR ::= SEQUENCE { 
  event			ADASEventType-KOR,
  distance		ObstacleDistance 	OPTIONAL,
  time			DSecond						OPTIONAL,
  lon			Longitude					OPTIONAL,
  lat			Latitude					OPTIONAL,
  confidence	PositionConfidence	OPTIONAL,
  ...
}

DetectedObject-KOR ::= SEQUENCE {
  objectID			OCTET STRING (SIZE(1..64)),
  objectType 		ITIScodes		OPTIONAL,
  objectLocation	FullPositionVector,
  ... 
}

DetectedObjectInfo-KOR ::= SEQUENCE {
  detectorID	UTF8String (SIZE(1..128)),
  objects			DetectedObjectList-KOR,
  ... 
}

DetectedObjectList-KOR ::= SEQUENCE (SIZE(1..32)) OF DetectedObject-KOR

EmergencyVehicleAlert-KOR ::= SEQUENCE {
  typeEvent		ITISCodes-KOR,
  heading 		Heading	      			OPTIONAL,
  extent		Extent		  				OPTIONAL,
  position		FullPositionVector	OPTIONAL,
  ...
}

EventDescription-KOR ::= SEQUENCE {
  eventType		ITISCodes-KOR,
  ... 
}

EventOrSvcInfo-KOR ::= SEQUENCE {
  typeEvent		ITIScodes						OPTIONAL,
  description	ITIScodesAndText		OPTIONAL,
  text				SEQUENCE (SIZE(1..8)) OF UTF8String	        OPTIONAL,
  subtext			SEQUENCE (SIZE(1..8)) OF UTF8String	        OPTIONAL,
  ...
}

FuelEfficiency-KOR ::= SEQUENCE {
  vehicleMileage	INTEGER	OPTIONAL,
  evMileage				INTEGER	OPTIONAL,
  ...
}

FuelResidualQuantity-KOR ::= SEQUENCE {
  vehiclePercent	INTEGER(0..100)	OPTIONAL,
  evPercent				INTEGER(0..100)	OPTIONAL,
  ...
}

FuelStatus-KOR ::= SEQUENCE {
  efficiency				FuelEfficiency-KOR 			OPTIONAL,
  residualQuantity	FuelResidualQuantity-KOR	OPTIONAL,
  tankCapacity			FuelTankCapacity-KOR 		OPTIONAL,
  ...
}

FuelTankCapacity-KOR ::= SEQUENCE {
  fuelCapacity	INTEGER(0..255) OPTIONAL,
  evCapacity		INTEGER(0..255) OPTIONAL,
  ...
  }

GeographicalPath-KOR ::= SEQUENCE {
  regions		SEQUENCE (SIZE(1..32)) OF RegionDescribedByID-KOR,
  ...
}

GyroscopeValue-KOR ::= SEQUENCE {
  xmax		INTEGER(-32767..32767) OPTIONAL,
  xmin		INTEGER(-32767..32767) OPTIONAL,
  xavg		INTEGER(-32767..32767) OPTIONAL,
  ymax		INTEGER(-32767..32767) OPTIONAL,
  ymin		INTEGER(-32767..32767) OPTIONAL,
  yavg		INTEGER(-32767..32767) OPTIONAL,
  zmax		INTEGER(-32767..32767) OPTIONAL,
  zmin		INTEGER(-32767..32767) OPTIONAL,
  zavg		INTEGER(-32767..32767) OPTIONAL,
  ...
}

IntersectionCollisionAvoidance-KOR ::= SEQUENCE {
  path    PathPlanned-KOR    OPTIONAL,
  ...
}

MsgLog-KOR ::= SEQUENCE {
  furtherInfoID    		FurtherInfoID,
  msgType 				MsgType-KOR, 
  msgEvent 				ITISCodes-KOR 		OPTIONAL,
  msgID          		TemporaryID,
  msgDate        		DDateTime					OPTIONAL,
  msgCommType			MsgCommType-KOR		OPTIONAL,
  msgChannel 			MsgChannel-KOR		OPTIONAL,
  msgDeviceType			MsgDeviceType-KOR,
  msgDisplayLocation 	MsgDisplayLocation-KOR	OPTIONAL,
  msgDisplayTime		DDateTime					OPTIONAL,
  ...
}

MsgLogs-KOR ::= SEQUENCE {
  rcvMsgs	SEQUENCE (SIZE(1..20)) OF MsgLog-KOR OPTIONAL,
  sndMsgs	SEQUENCE (SIZE(1..30)) OF MsgLog-KOR OPTIONAL,
  ...
}

ParkingCapacity-KOR ::= SEQUENCE {
  type 				    			ParkingType-KOR,
  numberOfParkingSpace	INTEGER,
  maxParkingSpace				INTEGER 	OPTIONAL,  
  ...
}

ParkingZoneInformation-KOR ::= SEQUENCE {
  name 			UTF8String (SIZE(1..128))	OPTIONAL,
  id				UTF8String (SIZE(1..128))	OPTIONAL,
  capacity	SEQUENCE (SIZE(0..16)) OF ParkingCapacity-KOR,
  ...
}

PersonalSafetyMessage-KOR ::= SEQUENCE {
  path					PathPlanned-KOR			OPTIONAL,
  ...
}

PathPlanned-KOR ::= SEQUENCE {
  initialPosition 	FullPositionVector 		OPTIONAL,
  currGNSSstatue  	GNSSstatus						OPTIONAL,
  pathPlanned	 			PathPlannedPointList-KOR,
  ...
}

PathPlannedPoint-KOR ::= SEQUENCE {
  latOffset       OffsetLL-B18,
  lonOffset       OffsetLL-B18,
  elevationOffset VertOffset-B12,
  timeOffset			TimeOffset,
  positionalAccuracy	PositionalAccuracy	OPTIONAL,	
  heading				CoarseHeading			OPTIONAL,
  ...
}

PathPlannedPointList-KOR ::= SEQUENCE (SIZE(1..32)) OF PathPlannedPoint-KOR

ProbeVehicleData-KOR ::= SEQUENCE {
  msgID					INTEGER(0..65535),
  curlane				DectLane-KOR,
  adas 					CITSADAS-KOR						OPTIONAL,
  driverStatus 			HumanDriverStatus-KOR		OPTIONAL,
  deviceStatus 			DeviceStatus-KOR				OPTIONAL,
  transitStatus			TransitVehicleStatus		OPTIONAL,
  transitOccupancy		TransitVehicleOccupancy	OPTIONAL,
  roadWorkInfo			RoadWorkInfo-KOR 				OPTIONAL,	
  eventOrSvcInfo		EventOrSvcInfo-KOR 			OPTIONAL,
  msgLogs				MsgLogs-KOR 						OPTIONAL,
  vehicleControlInfo	VehicleControlInfo-KOR 	OPTIONAL,
  drivingStatus			DrivingStatus-KOR 			OPTIONAL,
  fuelStatus			FuelStatus-KOR 					OPTIONAL,
  sensorValues			SensorValuesRegardingDriving-KOR OPTIONAL,
  ...
}

RegionDescribedByID-KOR ::= CHOICE {
  laneID		LaneID,		
  segmentID		RoadSegmentID,	
  linkID		UTF8String (SIZE(1..128)),
  detectLane	DectLane-KOR,	
  areaID     	UTF8String (SIZE(1..128)),	
  intersections	IntersectionID,
  ...
}

RidingNotification-KOR ::= SEQUENCE {
  stopID		UTF8String (SIZE(1..128))		OPTIONAL,
  disabled 	Disabled-KOR	OPTIONAL,
  boarding	BOOLEAN				OPTIONAL,
  ...
}

RoadSideAlert-KOR ::= SEQUENCE {
  msgID				INTEGER(0..65535)							OPTIONAL,
  regions			SEQUENCE OF RegionDescribedByID-KOR OPTIONAL,
  events 			EventOrSvcInfo-KOR						OPTIONAL,
  state				MovementEvent						OPTIONAL,
  detectedObject	DetectedObjectInfo-KOR		OPTIONAL,
  ...
}

RoadWorkInfo-KOR ::= SEQUENCE {
  worklanes		SEQUENCE (SIZE(1..16)) OF LaneID OPTIONAL,
  workstart		DDateTime OPTIONAL,
  workend		DDateTime OPTIONAL,
  ...
}

ServiceAreaInformation-KOR ::= SEQUENCE {
  name					UTF8String (SIZE(1..128)),
  id						UTF8String (SIZE(1..128)),
  direction			HighwayDirection-KOR,
  stationInfo		SEQUENCE OF StationInformation-KOR			OPTIONAL,
  parkingInfo		SEQUENCE OF ParkingZoneInformation-KOR	OPTIONAL,
  ...
}

SensorValuesRegardingDriving-KOR ::= SEQUENCE {
  rpm		Rpm-KOR				OPTIONAL,
  gears		TransmissionState 	OPTIONAL,
  gyro		GyroscopeValue-KOR	OPTIONAL,
  ...
}

StationInformation-KOR ::= SEQUENCE {
  type 		    	FuelType-KOR,
  capacity 	    INTEGER(0..256)	OPTIONAL,
  maxcapacity 	INTEGER(0..256)	OPTIONAL,
  price		    	INTEGER			OPTIONAL,
  ...
}

SupplementalVehicleExtensions-KOR ::= SEQUENCE {
  vehicleClass BasicVehicleClass-KOR, 
  ...
} 

TollgateLane-KOR ::= SEQUENCE {
  laneNo	DectLane-KOR		OPTIONAL,
  linkID	LaneID			OPTIONAL,
  type		TollgateType-KOR	OPTIONAL,
  open		BOOLEAN				OPTIONAL,
  ...
}

TollgateLaneInformation-KOR ::= SEQUENCE {
  name		UTF8String (SIZE(1..128)) 		OPTIONAL,
  heading	HighwayDirection-KOR	        OPTIONAL,
  lanes		SEQUENCE (SIZE(1..32)) OF            
  				TollgateLane-KOR			OPTIONAL,
  ...
}

TrafficLightStatus-KOR ::= SEQUENCE {
  trafficLightType		      TrafficLightType-KOR,
  consecutiveTrafficLight   ConsecutiveTrafficLight-KOR,
  trafficLightIntervalType	TrafficLightIntervalType-KOR,
  pedestrianCall		        PedestrianCall-KOR,
  actuatedinterval		      ActuatedInterval-KOR,
  permissiveNonProtected	  PermissiveNonProtected-KOR,
  lightingStatus		        TrafficLightingStatus-KOR,
  maxIntervalLength		      TimeInSecond-B8-KOR,
  remainingTime		          TimeInSecond-B8-KOR,
  directionCode		          TrafficLightDirectionCode-KOR,
  reserved			            ReservedBit-KOR,
  ... 
}

TrafficLightStatusList-KOR ::= SEQUENCE (SIZE(1..255)) OF TrafficLightStatus-KOR

TravelerDataFrameAdditionalInformation-KOR ::= SEQUENCE {
  dataFrameIndex			INTEGER(0..8),
  events 							EventOrSvcInfo-KOR					OPTIONAL,
  vehicleRidingStatus RidingNotification-KOR			OPTIONAL,
  weatherInfo					WeatherInfo-KOR							OPTIONAL,
  serviceArea					ServiceAreaInformation-KOR		OPTIONAL,
  tollgate						TollgateLaneInformation-KOR		OPTIONAL,
  ...
}

TravelerInformation-KOR ::= SEQUENCE {
  msgID			    INTEGER			OPTIONAL,
  additionalInfo 			SEQUENCE(SIZE(1..8)) OF 
							TravelerDataFrameAdditionalInformation-KOR			OPTIONAL,
  ...
}

VehicleClassification-KOR ::= SEQUENCE {
  role		BasicVehicleRole-KOR 		OPTIONAL,
  ...
}

VehicleControlInfo-KOR ::= SEQUENCE {
  mode			VehicleControlMode-KOR	OPTIONAL,
  turning		PossibleTurn-KOR				OPTIONAL,
  angle			DrivingWheelAngle 			OPTIONAL,
  ...
}

WeatherInfo-KOR ::= SEQUENCE {
  temp		AmbientAirTemperature 	OPTIONAL,
  rainfall	EssPrecipRate			OPTIONAL,
  humidity	INTEGER(0..100)				OPTIONAL,
  windDir 	HeadingSlice			OPTIONAL,
  windSpd	INTEGER(0..10000)			OPTIONAL,
  ...
}

WheelAngles-KOR ::= SEQUENCE {
  flWheelAngle		DrivingWheelAngle	OPTIONAL, 	
  frWheelAngle		DrivingWheelAngle	OPTIONAL, 	
  rlWheelAngle		DrivingWheelAngle	OPTIONAL, 	
  rrWheelAngle		DrivingWheelAngle	OPTIONAL
}

ITIScodesAndText ::= SEQUENCE (SIZE(1..100)) OF SEQUENCE {
  item CHOICE    {
    itis ITIScodes,
    text ITIStext
  }
}

TLS ::= SEQUENCE { 
    trafficLightID       TrafficLightID, 

    
    
    lon                Longitude   OPTIONAL,

    
    
    lat                 Latitude    OPTIONAL,

    
    
    operationStatus     TrafficLightOperationStatus,

    
    controllerStatus    TrafficLightControllerStatus,

    
    cyclecounter        TimeInSecond-B16, 

    
    cycletime           TimeInSecond-B16, 

    
    currentTime         DDateTime,

    
    trafficLightStatus  TrafficLightStatusList,

    
    ...

}







TrafficLightID ::= CHOICE {

    id  INTEGER,            
    oid OBJECT IDENTIFIER   
}






TrafficLightStatusList ::= SEQUENCE (SIZE(1..255)) OF TrafficLightStatus




TrafficLightStatus ::= SEQUENCE {

    trafficLightType            TrafficLightType,

    
    
    consecutiveTrafficLight     ConsecutiveTrafficLight,

    
    
    
    
    trafficLightIntervalType    TrafficLightIntervalType,

    
    pedestrianCall              PedestrianCall,

    
    actuatedinterval            ActuatedInterval,

    
    permissiveNonProtected      PermissiveNonProtected,

    
    lightingStatus              TrafficLightingStatus,

    
    maxIntervalLength           TimeInSecond-B8,

    
    remainingTime               TimeInSecond-B8,

    
    directionCode               TrafficLightDirectionCode,

    
    reserved                    ReservedBit,

    
    ...

}




J1939DataItems ::= SEQUENCE { 
   
   tires                    TireDataList              OPTIONAL,

   
   axles                    AxleWeightList            OPTIONAL,      

   trailerWeight            TrailerWeight             OPTIONAL,     

   cargoWeight              CargoWeight               OPTIONAL, 

   steeringAxleTemperature  SteeringAxleTemperature   OPTIONAL, 

   driveAxleLocation        DriveAxleLocation         OPTIONAL, 

   driveAxleLiftAirPressure DriveAxleLiftAirPressure  OPTIONAL, 

   driveAxleTemperature     DriveAxleTemperature      OPTIONAL, 

   driveAxleLubePressure    DriveAxleLubePressure     OPTIONAL, 

   steeringAxleLubePressure SteeringAxleLubePressure  OPTIONAL, 

   ...

   }   




SignalRequestMessage ::= SEQUENCE {    

   timeStamp       MinuteOfTheYear  OPTIONAL,

   second          DSecond,

   sequenceNumber  MsgCount         OPTIONAL,



   requests        SignalRequestList OPTIONAL,

                   
                   


   requestor       RequestorDescription,

                   
                   
                   
                   


   regional        SEQUENCE (SIZE(1..4)) OF 

                   RegionalExtension {{Reg-SignalRequestMessage}} OPTIONAL,

   ...

   }







SignalStatusMessage ::= SEQUENCE {

   timeStamp       MinuteOfTheYear  OPTIONAL,

   second          DSecond,

   sequenceNumber  MsgCount         OPTIONAL,            



   
   status          SignalStatusList,

 

   regional        SEQUENCE (SIZE(1..4)) OF 

                   RegionalExtension {{Reg-SignalStatusMessage}} OPTIONAL,

   ...

   }







Reg-SignalRequestMessage   REG-EXT-ID-AND-TYPE ::= { ... }


WheelAngle-KOR ::= SEQUENCE {

   flWheelAngle        DrivingWheelAngle     OPTIONAL,

   frWheelAngle        DrivingWheelAngle     OPTIONAL,

   rlWheelAngle        DrivingWheelAngle     OPTIONAL,

   rrWheelAngle        DrivingWheelAngle     OPTIONAL

}




DetectedObjectList ::= SEQUENCE (SIZE(1..256)) OF DetectedObjectData




DetectedObjectData::= SEQUENCE {

    detObjCommon    DetectedObjectCommonData,

    
    detObjOptData   DetectedObjectOptionalData OPTIONAL

    
}




DetectedObjectCommonData::= SEQUENCE {

    objType             ObjectType,

    objTypeCfd          ClassificationConfidence,

    objectID            ObjectID,

    
    measurementTime     MeasurementTimeOffset,

    
    timeConfidence      TimeConfidence,

    pos                 PositionOffsetXYZ,

    posConfidence       PositionConfidenceSet,

    speed               Speed,

    speedConfidence     SpeedConfidence,

    speedZ              Speed OPTIONAL,

    speedConfidenceZ    SpeedConfidence OPTIONAL,

    heading             Heading,

    headingConf         HeadingConfidence,

    accel4way           AccelerationSet4Way OPTIONAL,

    accCfdX             AccelerationConfidence OPTIONAL,

    accCfdY             AccelerationConfidence OPTIONAL,

    accCfdZ             AccelerationConfidence OPTIONAL,

    accCfdYaw           YawRateConfidence OPTIONAL,

    ...

}








DetectedObjectOptionalData ::= CHOICE {

    detVeh      DetectedVehicleData,

    
    detVRU      DetectedVRUData,

    
    detObst     DetectedObstacleData

    
}




DetectedVehicleData::= SEQUENCE {

    lights                  ExteriorLights              OPTIONAL,

    vehAttitude             Attitude                    OPTIONAL,

    vehAttitudeConfidence   AttitudeConfidence          OPTIONAL,

    vehAngVel               AngularVelocity             OPTIONAL,

    vehAngVelConfidence     AngularVelocityConfidence   OPTIONAL,

    size                    VehicleSize                 OPTIONAL,

    height                  VehicleHeight               OPTIONAL,

    vehicleSizeConfidence   VehicleSizeConfidence       OPTIONAL,

    vehicleClass            BasicVehicleClass           OPTIONAL,

    classConf               ClassificationConfidence    OPTIONAL,

    ...

}




Attitude ::= SEQUENCE {

    pitch   PitchDetected,

    roll    RollDetected,

    yaw     YawDetected

}




AttitudeConfidence ::= SEQUENCE {

    pitchConfidence     HeadingConfidence,

    rollConfidence      HeadingConfidence,

    yawConfidence       HeadingConfidence

}




AngularVelocity ::= SEQUENCE {

    pitchRate   PitchRate,

    rollRate    RollRate

}




AngularVelocityConfidence ::= SEQUENCE {

    pitchRateConfidence PitchRateConfidence OPTIONAL,

    rollRateConfidence RollRateConfidence OPTIONAL

}




VehicleSizeConfidence ::= SEQUENCE {

    vehicleWidthConfidence      SizeValueConfidence,

    vehicleLengthConfidence     SizeValueConfidence,

    vehicleHeightConfidence     SizeValueConfidence OPTIONAL

}




DetectedVRUData::= SEQUENCE {

    basicType       PersonalDeviceUserType  OPTIONAL,

    propulsion      PropelledInformation    OPTIONAL,

    attachment      Attachment              OPTIONAL,

    radius          AttachmentRadius        OPTIONAL

}




DetectedObstacleData::= SEQUENCE {

    obstSize            ObstacleSize,

    obstSizeConfidence  ObstacleSizeConfidence

}




ObstacleSize ::= SEQUENCE {

    width   SizeValue,

    length  SizeValue,

    height  SizeValue   OPTIONAL

}




ObstacleSizeConfidence ::= SEQUENCE {

    widthConfidence     SizeValueConfidence,

    lengthConfidence    SizeValueConfidence,

    heightConfidence    SizeValueConfidence     OPTIONAL

}




PositionOffsetXYZ ::= SEQUENCE {

    offsetX     ObjectDistance,

    offsetY     ObjectDistance,

    offsetZ     ObjectDistance OPTIONAL

}




SensorDataSharingMessage ::= SEQUENCE {

    msgCnt              MsgCount,

    sourceID            TemporaryID,

    equipmentType       EquipmentType,

    sDSMTimeStamp       DDateTime,

    refPos              Position3D,

    refPosXYConf        PositionalAccuracy,

    refPosElConf        ElevationConfidence     OPTIONAL,

    objects             DetectedObjectList

}

END
